SOCOMEC-DIRIS-PRODUCTS-MIB DEFINITIONS ::= BEGIN

IMPORTS
    MODULE-COMPLIANCE, OBJECT-GROUP, NOTIFICATION-GROUP 
        FROM SNMPv2-CONF           
        
    MODULE-IDENTITY, OBJECT-TYPE, NOTIFICATION-TYPE,
    Integer32, Unsigned32, enterprises
        FROM SNMPv2-SMI
       
    DisplayString, RowStatus, StorageType
        FROM SNMPv2-TC;

    -- *******************************************************************************
    -- Definition of Socomec Enumerations ********************************************
    SocomecCircuitType ::= TEXTUAL-CONVENTION
        STATUS       current
        DESCRIPTION  "Socomec enumeration for Circuit Type"
        SYNTAX       INTEGER {  none(0),
                                e1PN-1CT(1),
                                e2P-1CT(2), e2PN-2CT(3),
                                e3P-1CT(4), e3P-2CT(5), e3P-3CT(6),
                                e3PN-1CT(7), e3PN-3CT(8), e3PN-4CT(9),
                                multifluid(10),
                                dc(11),
                                e1CT(12),e3CT(13),
                                isomFeeder(14),
                                rcm(15),ups(16)
                                }

    SocomecCircuitNature ::= TEXTUAL-CONVENTION
        STATUS       current
        DESCRIPTION  "Socomec enumeration for Circuit Nature"
        SYNTAX       INTEGER {  electricity(0),
                                gas(1),
                                water(2),
                                compressedAir(3),
                                fuel(4),
                                undefined(5),
                                fluid1(6),
                                fluid2(7),
                                fluid3(8),
                                custom(9)
                                }

    SocomecCircuitUsage ::= TEXTUAL-CONVENTION
        STATUS       current
        DESCRIPTION  "Socomec enumeration for Circuit Usage"
        SYNTAX       INTEGER {  heating(0),
                                ventilation(1),
                                airConditionning(2),
                                auxiliaryFanPump(3),
                                indoorLighting(4),
                                outdoorLighting(5),
                                socket(6),
                                hotWaterDomestic(7),
                                hotWater(8),
                                coldWater(9),
                                iceWater(10),
                                refrigeratingProduction(11),
                                photovoltaics(12),
                                wind(13),
                                it(14),
                                process(15),
                                usage1(16),
                                usage2(17),
                                usage3(18),
                                undefined(19),
                                custom(20),
                                insulation(21)
                                }

    SocomecBreakerPosition ::= TEXTUAL-CONVENTION
        STATUS       current
        DESCRIPTION  "Socomec enumeration for Breaker Position"
        SYNTAX       INTEGER { opened(0), closed(1), unknown(2), na(3) }

    SocomecTripStatus ::= TEXTUAL-CONVENTION
        STATUS       current
        DESCRIPTION  "Socomec enumeration for Trip Status"
        SYNTAX       INTEGER { noTrip(0), trip(1), unknown(2) }

    SocomecTripCause ::= TEXTUAL-CONVENTION
        STATUS       current
        DESCRIPTION  "Socomec enumeration for Trip Cause"
        SYNTAX       INTEGER { overcurrent(0), differential(1), bothOvercurrentDifferential(2), unknown(3) }

    SocomecBreakerFault ::= TEXTUAL-CONVENTION
        STATUS       current
        DESCRIPTION  "Socomec enumeration for Breaker fault"
        SYNTAX       INTEGER { none(0), fault(1) }

    SocomecModeDigitalIO ::= TEXTUAL-CONVENTION
        STATUS       current
        DESCRIPTION  "Socomec enumeration for ditial mode"
        SYNTAX       INTEGER {  normallyOpen(0), normallyClosed(1) }

    SocomecModeAnalogIO ::= TEXTUAL-CONVENTION
        STATUS       current
        DESCRIPTION  "Socomec enumeration for analog mode"
        SYNTAX       INTEGER {  e0-20mA(0), e4-20mA(1) }

    SocomecIOFunctions ::= TEXTUAL-CONVENTION
        STATUS       current
        DESCRIPTION  "Socomec enumeration for IO functions"
        SYNTAX       INTEGER {  none(0),
                                -- Input Functions:
                                pulseMeter(3), logicalAlarm(4), alarmAck(5), breaker(9), extTopSynchro(10), tarif(11),
                                productTest(15), imdInjection(16), lciInjection(17),
                                forceOff(18), tokenDgw(19), tokenEth(20),
                                -- ATS input:
                                inh(21), inhp(22), inht(23), ton(24), tof(25), eon(26), eof(27), rtc(28), pri(29),
                                ss1(30), ss2(31), ale(32), fte(33), msr(36), oa1(37), oa2(38), ou1(39),
                                ou2(40), rst(41), lsi(42), ac1(43), ac2(44), ac0(45), ac0a(46), ac0b(47), man(48), lck(49),
                                chp(50), iee(51), pop(52), ps1(53), ps2(54), ps0(55), rt0(56), blk(57), tp1(58), tp2(59),
                                rec(60), est(61), ipi(62), ipb(63), bct(64), elb(65), is1(66), is2(67),
                                screen(100), shutter(101),
                             
                                -- Output Functions:
                                alarmReport(6), imdInjection(7), lciInjection (8) ,
                                loadShedding(12), energyPulse(13), topSynchroReport(14),

                                -- ATS output:
                                po1(70), po2(71), po0(72), pa0(73), pb0(74), gs1(75), gs2(76), s1a(77), s2a(78), sca(79),
                                s1u(80), s2u(81), ac1(82), ac2(83), ac0(84), lo1(85), lo2(86), lsc(87), flt(88), pop(89),
                                lck(90), cop(91), tos(92), eos(93), ros(94), pts(95), ees(96), tpp(97), tpt(98), ipt(99),
                                phi(100), co1(101), co2(102), co3(103), co4(104), co5(105), co6(106), eea(107), elv(108)
                                }

SocomecAtsSourcePrio ::= TEXTUAL-CONVENTION
        STATUS       current
        DESCRIPTION  "Socomec enumeration for Ats Source prio"
        SYNTAX       INTEGER {  network(0), source1(1), source2(2) }

SocomecAtsOperatingMode ::= TEXTUAL-CONVENTION
        STATUS       current
        DESCRIPTION  "Socomec enumeration for Ats Operating Mode"
        SYNTAX       INTEGER { manual(0), locked(1), auto(16), remote(32), inhibit(64) }

SocomecAtsPosition ::= TEXTUAL-CONVENTION
        STATUS       current
        DESCRIPTION  "Socomec enumeration for Ats Position"
        SYNTAX       INTEGER { unknown(0), position0(1), position1(2), position2(3) }

SocomecAtsStateSource ::= TEXTUAL-CONVENTION
        STATUS       current
        DESCRIPTION  "Socomec enumeration for Ats State of Source"
        SYNTAX       INTEGER { underThreshold(0), present(1), available(2) }

SocomecAtsTestInProgress ::= TEXTUAL-CONVENTION
        STATUS       current
        DESCRIPTION  "Socomec enumeration for Ats Test in progress"
        SYNTAX       INTEGER { none(0), tof(1), eof(2), tol(4), eol(8) }

SocomecAtsAlarmFault ::= TEXTUAL-CONVENTION
        STATUS       current
        DESCRIPTION  "Socomec enumeration for Ats alarm fault"
        SYNTAX       INTEGER {  none(0),
                                operatingFactor(1), neutralPosition(2),
                                fault1(3), fault2(4), alarm1(5), alarm2(6), rotationSource1(7), rotationSource2(8),
                                capaSource1(9), capaSource2(10), powerSource1(11), powerSource2(12),
                                position1(13), position2(14), position0(15), fault0(16),
                                unbalancedSource1(17), unbalancedSource2(18), mainFault(19),
                                motorFault(20), autoconfigurationFailed(21), unknownOrMultiple(255) }

SocomecAtsSwitchFaultSummary ::= TEXTUAL-CONVENTION
        STATUS       current
        DESCRIPTION  "Socomec enumeration for Ats Fault summary"
        SYNTAX       INTEGER {  none(0), alarm(1), fault(2) }

SocomecAtsSwitchLastCause ::= TEXTUAL-CONVENTION
        STATUS       current
        DESCRIPTION  "Socomec enumeration for Ats last switch cause"
        SYNTAX       INTEGER {  none(0), manual(1),
                                underVoltageSource1(2), underVoltageSource2(3), overVoltageSource1(4), overVoltageSource2(5),
                                underFrequenceSource1(6), underFrequenceSource2(7), overFrequenceSource1(8), overFrequenceSource2(9),
                                unbalancedSource1(10), unbalancedSource2(11), rotationSource1(12), rotationSource2(13),
                                prioritySource(14), remote(15) }

SocomecAlarmType ::= TEXTUAL-CONVENTION
        STATUS       current
        DESCRIPTION  "Socomec enumeration for Alarm Type"
        SYNTAX       INTEGER {  analogicalAlarms(1),logicalAlarms(2), combinationAlarms(3), en50160Alarms(4), inrushAlarms(5), 
                                systemAlarms(6), isomAlarms(7), customAlarms(8), booleanAlarms(9), rcmAlarms(10),
                                faultAlarms(11), comparisonAlarms(12) }

    -- *******************************************************************************
    -- Definition of Identification Entry ********************************************
    SeqIdentificationEnt ::= SEQUENCE {
                   identModbusAddress    Unsigned32,
                   identProductIndex     Unsigned32,
                   identProductRowStatus RowStatus,
				   identTypeProduct      Unsigned32,
                   identType             DisplayString,     -- IDeviceId
                   identSWVersion        DisplayString,     -- IMajorProdVersion.IMinorProdVersion.IRevisionProdVersion.IBuildProdVersion
                   identVersionBuildDate DisplayString,     -- IBuildDateProdVersion
                   identSerialAASS       Unsigned32,
                   identSerialSSTL       Unsigned32,
                   identSerialOrder      Unsigned32,
                   identSerialReserve    Unsigned32,
                   identOperatingCounter Unsigned32         -- Does Not Exist so far ...
                   }

    -- *******************************************************************************
    -- Definition of Circuit Entry ********************************************
    SeqCircuitEnt ::= SEQUENCE {
                   circuitIndex            Unsigned32,
                   circuitProductIndex     Unsigned32,
                   circuitProductLine      Unsigned32,
                   circuitProductModbusAddress Unsigned32,
                   circuitRowStatus        RowStatus,
                   circuitName             DisplayString,
                   circuitType             SocomecCircuitType,
                   circuitUsage            SocomecCircuitUsage,
                   circuitNature           SocomecCircuitNature,
                   circuitLocation         DisplayString,
                   }

    -- *******************************************************************************
    -- Definition of Metrology Load Curves Entry *************************************
    SeqLoadCurvesEnt ::= SEQUENCE {            
                   loadCurvesModbusAddress       Unsigned32,
                   loadCurvesProductIndex       Unsigned32,
                   loadCurvesLoadIndex          Unsigned32,
                   loadCurvesLoadRowStatus      RowStatus,
                   loadCurvesActivePowerPos     Unsigned32,
                   loadCurvesActivePowerNeg     Unsigned32,
                   loadCurvesReactivePowerPos   Unsigned32,
                   loadCurvesReactivePowerNeg   Unsigned32,
                   loadCurvesApparentPower      Unsigned32 
                   }

    -- *******************************************************************************
    -- Definition of Metrology Energy Entry
    SeqEnergyEnt ::= SEQUENCE {            
                   engModbusAddress      Unsigned32,
                   engProductIndex       Unsigned32,
                   engLoadIndex          Unsigned32,
                   engLoadRowStatus      RowStatus,
				   engTotalHourMeter                           Unsigned32,
                   engTotalEnergyActivePos                     Unsigned32,
                   engTotalEnergyActiveResidualPos             Unsigned32,
                   engTotalEnergyActiveNeg                     Unsigned32,
                   engTotalEnergyActiveResidualNeg             Unsigned32,
                   engTotalEnergyReactivePos                   Unsigned32,
                   engTotalEnergyReactiveResidualPos           Unsigned32,
                   engTotalEnergyReactiveNeg                   Unsigned32,
                   engTotalEnergyReactiveResidualNeg           Unsigned32,
                   engTotalEnergyApparent                      Unsigned32,
                   engTotalEnergyApparentResidual              Unsigned32,
                   engTotalEnergyReactiveLaggingPos            Unsigned32,
                   engTotalEnergyReactiveLaggingResidualPos    Unsigned32,
                   engTotalEnergyReactiveLaggingNeg            Unsigned32,
                   engTotalEnergyReactiveLaggingResidualNeg    Unsigned32,
                   engTotalEnergyReactiveLeadingPos            Unsigned32,
                   engTotalEnergyReactiveLeadingResidualPos    Unsigned32,
                   engTotalEnergyReactiveLeadingNeg            Unsigned32,
                   engTotalEnergyReactiveLeadingResidualNeg    Unsigned32,
                   engPartialHourMeter                         Unsigned32,
                   engPartialEnergyActivePos                   Unsigned32,
                   engPartialEnergyActiveResidualPos           Unsigned32,
                   engPartialEnergyActiveNeg                   Unsigned32,
                   engPartialEnergyActiveResidualNeg           Unsigned32,
                   engPartialEnergyReactivePos                 Unsigned32,
                   engPartialEnergyReactiveResidualPos         Unsigned32,
                   engPartialEnergyReactiveNeg                 Unsigned32,
                   engPartialEnergyReactiveResidualNeg         Unsigned32,
                   engPartialEnergyApparent                    Unsigned32,
                   engPartialEnergyApparentResidual            Unsigned32,
                   engLastPartialResetDate                     Unsigned32,
                   --engLastPartialHourMeter                   Unsigned32,
                   engLastPartialEnergyActivePos               Unsigned32,
                   engLastPartialEnergyActiveResidualPos       Unsigned32,
                   engLastPartialEnergyActiveNeg               Unsigned32,
                   engLastPartialEnergyActiveResidualNeg       Unsigned32,
                   engLastPartialEnergyReactivePos             Unsigned32,
                   engLastPartialEnergyReactiveResidualPos     Unsigned32,
                   engLastPartialEnergyReactiveNeg             Unsigned32,
                   engLastPartialEnergyReactiveResidualNeg     Unsigned32,
                   engLastPartialEnergyApparent                Unsigned32,
                   engLastPartialEnergyApparentResidual        Unsigned32
                   }

    -- *******************************************************************************
    -- Definition of Product Measurement Instantaneous Entry *************************
    -- Definition of Metrology Multifluid Entry
    SeqMultifluidEnt ::= SEQUENCE {            
                   mffModbusAddress      Unsigned32,
                   mffProductIndex       Unsigned32,
                   mffLoadIndex          Unsigned32,
                   mffLoadRowStatus      RowStatus,
                   mffTotalMeter         Integer32,
                   mffPartialMeter       Integer32,
                   mffUnit               DisplayString,
                   mffWeight             Integer32
                   }

    -- *******************************************************************************
    -- Definition of Product Measurement Instantaneous Entry *************************
    SeqInstantaneousEnt ::= SEQUENCE {            
                   instModbusAddress         Unsigned32,
                   instProductIndex         Unsigned32,
                   instLoadIndex            Unsigned32,
                   instLoadRowStatus        RowStatus,
                   --instDateLastInstance     Unsigned32,
                -- 1x ==> System Measurements
                   instVoltSystPhN          Unsigned32,
                   instVoltSystPhPh         Unsigned32,
                   instCurrentSyst          Unsigned32,
                   instFrequency            Unsigned32,
                -- 2x/3x ==> Voltage Measurements
                   instVoltPhNV1            Unsigned32,
                   instVoltPhNV2            Unsigned32,
                   instVoltPhNV3            Unsigned32,
                   instVoltPhNVn            Unsigned32,
                   instVoltPhPhU12          Unsigned32,
                   instVoltPhPhU23          Unsigned32,
                   instVoltPhPhU31          Unsigned32,
                -- 4x/5x ==> Current Measurements
                   instCurrentI1            Unsigned32,
                   instCurrentI2            Unsigned32,
                   instCurrentI3            Unsigned32, 
                   instCurrentIn            Unsigned32,
                   instCurrentInba          Unsigned32,
                   instCurrentIdir          Unsigned32,
                   instCurrentIinv          Unsigned32,
                   instCurrentIhom          Unsigned32,
                   instCurrentInb           Unsigned32,
                   instCurrentIdn           Unsigned32,
                   instCurrentIpe           Unsigned32,
                -- 6x/7x ==> Total Power Measurements
                   instPowerApparentNom     Unsigned32,
                   instTotalPowerActive     Integer32,
                   instTotalPowerReactive   Integer32,
                   instTotalPowerApparent   Unsigned32,
                   instTotalPowerFactor     Integer32,
                   instTotalPowerFactorType Unsigned32,
                -- 8x/9x ==> Phasis Power Measurements
                   instPowerActiveP1        Integer32,
                   instPowerActiveP2        Integer32,
                   instPowerActiveP3        Integer32,
                   instPowerReactiveQ1      Integer32,
                   instPowerReactiveQ2      Integer32,
                   instPowerReactiveQ3      Integer32,
                   instPowerApparentS1      Unsigned32,
                   instPowerApparentS2      Unsigned32,
                   instPowerApparentS3      Unsigned32,
                -- 10x ==> Power Factor Measurements
                   instPowerFactorPF1       Integer32,
                   instPowerFactorTypeSPF1  Unsigned32,
                   instPowerFactorPF2       Integer32,
                   instPowerFactorTypeSPF2  Unsigned32,
                   instPowerFactorPF3       Integer32,
                   instPowerFactorTypeSPF3  Unsigned32
                   }

    -- *******************************************************************************
    -- Definition of Averages Entry **************************************************
    SeqAveragesEnt ::= SEQUENCE {            
				   avgModbusAddress        Unsigned32,
                   avgProductIndex         Unsigned32,
                   avgLoadIndex            Unsigned32,
                   avgLoadRowStatus        RowStatus,
                   avgDateLastInstance     Unsigned32,
                -- 1x ==> System Measurements
                   avgVoltSystPhN          Unsigned32,
                   avgVoltSystPhPh         Unsigned32,
                   avgCurrentSyst          Unsigned32,
                   avgFrequency            Unsigned32,
                -- 2x/3x ==> Voltage Measurements
                   avgVoltPhNV1            Unsigned32,
                   avgVoltPhNV2            Unsigned32,
                   avgVoltPhNV3            Unsigned32,
                   avgVoltPhNVn            Unsigned32,
                   avgVoltPhPhU12          Unsigned32,
                   avgVoltPhPhU23          Unsigned32,
                   avgVoltPhPhU31          Unsigned32,
                -- 4x/5x ==> Current Measurements
                   avgCurrentI1            Unsigned32,
                   avgCurrentI2            Unsigned32,
                   avgCurrentI3            Unsigned32, 
                   avgCurrentIn            Unsigned32,
                   avgCurrentInba          Unsigned32,
                   avgCurrentIdir          Unsigned32,
                   avgCurrentIinv          Unsigned32,
                   avgCurrentIhom          Unsigned32,
                   avgCurrentInb           Unsigned32,
                -- 6x/7x ==> Total Power Measurements
                   avgTotalPowerActive     Integer32,
                   avgTotalPowerReactive   Integer32,
                   avgTotalPowerApparent   Unsigned32,
                   avgTotalPowerFactor     Integer32,
                   avgTotalPowerFactorType Unsigned32,
                -- 8x/9x ==> Phasis Power Measurements
                   avgPowerActiveP1        Integer32,
                   avgPowerActiveP2        Integer32,
                   avgPowerActiveP3        Integer32,
                   avgPowerReactiveQ1      Integer32,
                   avgPowerReactiveQ2      Integer32,
                   avgPowerReactiveQ3      Integer32,
                   avgPowerApparentS1      Unsigned32,
                   avgPowerApparentS2      Unsigned32,
                   avgPowerApparentS3      Unsigned32,
                -- 10x ==> Power Factor Measurements
                   avgPowerFactorPF1       Integer32,
                   avgPowerFactorTypeSPF1  Unsigned32,
                   avgPowerFactorPF2       Integer32,
                   avgPowerFactorTypeSPF2  Unsigned32,
                   avgPowerFactorPF3       Integer32,
                   avgPowerFactorTypeSPF3  Unsigned32
                   }

    -- *******************************************************************************
    -- Definition of Product Measurement Max Instantaneous Entry *********************
    SeqMaxInstantaneousEnt ::= SEQUENCE {            
                   maxInstModbusAddress         Unsigned32,
                   maxInstProductIndex         Unsigned32,
                   maxInstLoadIndex            Unsigned32,
                   maxInstLoadRowStatus        RowStatus,
                -- 1x ==> System Measurements
                   maxInstFrequency            Unsigned32,
                   maxInstFrequencyDate        Unsigned32,
                -- 2x/3x ==> Voltage Measurements
                   maxInstVoltPhNV1            Unsigned32,
                   maxInstVoltPhNV1Date        Unsigned32,
                   maxInstVoltPhNV2            Unsigned32,
                   maxInstVoltPhNV2Date        Unsigned32,
                   maxInstVoltPhNV3            Unsigned32,
                   maxInstVoltPhNV3Date        Unsigned32,
                   maxInstVoltPhNVn            Unsigned32,
                   maxInstVoltPhNVnDate        Unsigned32,
                   maxInstVoltPhPhU12          Unsigned32,
                   maxInstVoltPhPhU12Date      Unsigned32,
                   maxInstVoltPhPhU23          Unsigned32,
                   maxInstVoltPhPhU23Date      Unsigned32,
                   maxInstVoltPhPhU31          Unsigned32,
                   maxInstVoltPhPhU31Date      Unsigned32,
                -- 4x/5x ==> Current Measurements
                   maxInstCurrentI1            Unsigned32, 
                   maxInstCurrentI1Date        Unsigned32,
                   maxInstCurrentI2            Unsigned32, 
                   maxInstCurrentI2Date        Unsigned32,
                   maxInstCurrentI3            Unsigned32, 
                   maxInstCurrentI3Date        Unsigned32, 
                   maxInstCurrentIn            Unsigned32, 
                   maxInstCurrentInDate        Unsigned32,
                -- 6x/7x ==> Total Power Measurements
                   maxInstTotalPowerActive         Integer32,  
                   maxInstTotalPowerActiveDate     Unsigned32,
                   maxInstTotalPowerReactive       Integer32,
                   maxInstTotalPowerReactiveDate   Unsigned32,
                   maxInstTotalPowerApparent       Unsigned32, 
                   maxInstTotalPowerApparentDate   Unsigned32,
                   maxInstTotalPowerFactor         Integer32,
                   maxInstTotalPowerFactorType     Unsigned32,
                   maxInstTotalPowerFactorDate     Unsigned32,
                -- 8x/9x ==> Phasis Power Measurements
                   maxInstPowerActiveP1        Integer32,
                   maxInstPowerActiveP1Date    Unsigned32,
                   maxInstPowerActiveP2        Integer32,
                   maxInstPowerActiveP2Date    Unsigned32,
                   maxInstPowerActiveP3        Integer32,
                   maxInstPowerActiveP3Date    Unsigned32,
                   maxInstPowerReactiveQ1      Integer32,
                   maxInstPowerReactiveQ1Date  Unsigned32,
                   maxInstPowerReactiveQ2      Integer32,
                   maxInstPowerReactiveQ2Date  Unsigned32,
                   maxInstPowerReactiveQ3      Integer32,
                   maxInstPowerReactiveQ3Date  Unsigned32,
                   maxInstPowerApparentS1      Unsigned32,
                   maxInstPowerApparentS1Date  Unsigned32,
                   maxInstPowerApparentS2      Unsigned32,
                   maxInstPowerApparentS2Date  Unsigned32,
                   maxInstPowerApparentS3      Unsigned32,
                   maxInstPowerApparentS3Date  Unsigned32,
                -- 10x ==> Power Factor Measurements
                   maxInstPowerFactorPF1       Integer32, 
                   maxInstPowerFactorTypeSPF1  Unsigned32,
                   maxInstPowerFactorPF1Date   Unsigned32, 
                   maxInstPowerFactorPF2       Integer32, 
                   maxInstPowerFactorTypeSPF2  Unsigned32,
                   maxInstPowerFactorPF2Date   Unsigned32,
                   maxInstPowerFactorPF3       Integer32,
                   maxInstPowerFactorTypeSPF3  Unsigned32,
                   maxInstPowerFactorPF3Date   Unsigned32
                   }

    -- *******************************************************************************
    -- Definition of Product Measurement Min Instantaneous Entry *********************
    SeqMinInstantaneousEnt ::= SEQUENCE {
                    minInstModbusAddress            Unsigned32,
                    minInstProductIndex             Unsigned32,
                    minInstLoadIndex                Unsigned32,
                    minInstLoadRowStatus            RowStatus,
                --  1x ==> System Measurements
                    minInstFrequency                Unsigned32,
                    minInstFrequencyDate            Unsigned32,
                --  2x/3x ==> Voltage Measurements
                    minInstVoltPhNV1                Unsigned32,
                    minInstVoltPhNV1Date            Unsigned32,
                    minInstVoltPhNV2                Unsigned32,
                    minInstVoltPhNV2Date            Unsigned32,
                    minInstVoltPhNV3                Unsigned32,
                    minInstVoltPhNV3Date            Unsigned32,
                    minInstVoltPhNVn                Unsigned32,
                    minInstVoltPhNVnDate            Unsigned32,
                    minInstVoltPhPhU12              Unsigned32,
                    minInstVoltPhPhU12Date          Unsigned32,
                    minInstVoltPhPhU23              Unsigned32,
                    minInstVoltPhPhU23Date          Unsigned32,
                    minInstVoltPhPhU31              Unsigned32,
                    minInstVoltPhPhU31Date          Unsigned32,
                --  4x/5x ==> Current Measurements
                    minInstCurrentI1                Unsigned32,
                    minInstCurrentI1Date            Unsigned32,
                    minInstCurrentI2                Unsigned32,
                    minInstCurrentI2Date            Unsigned32,
                    minInstCurrentI3                Unsigned32,
                    minInstCurrentI3Date            Unsigned32,
                    minInstCurrentIn                Unsigned32,
                    minInstCurrentInDate            Unsigned32,
                --  6x/7x ==> Total Power Measurements
                    minInstTotalPowerActive         Integer32,
                    minInstTotalPowerActiveDate     Unsigned32,
                    minInstTotalPowerReactive       Integer32,
                    minInstTotalPowerReactiveDate   Unsigned32,
                    minInstTotalPowerApparent       Unsigned32,
                    minInstTotalPowerApparentDate   Unsigned32,
                    minInstTotalPowerFactor         Integer32,
                    minInstTotalPowerFactorType     Unsigned32,
                    minInstTotalPowerFactorDate     Unsigned32,
                --  8x/9x ==> Phasis Power Measurements
                    minInstPowerActiveP1            Integer32,
                    minInstPowerActiveP1Date        Unsigned32,
                    minInstPowerActiveP2            Integer32,
                    minInstPowerActiveP2Date        Unsigned32,
                    minInstPowerActiveP3            Integer32,
                    minInstPowerActiveP3Date        Unsigned32,
                    minInstPowerReactiveQ1          Integer32,
                    minInstPowerReactiveQ1Date      Unsigned32,
                    minInstPowerReactiveQ2          Integer32,
                    minInstPowerReactiveQ2Date      Unsigned32,
                    minInstPowerReactiveQ3          Integer32,
                    minInstPowerReactiveQ3Date      Unsigned32,
                    minInstPowerApparentS1          Unsigned32,
                    minInstPowerApparentS1Date      Unsigned32,
                    minInstPowerApparentS2          Unsigned32,
                    minInstPowerApparentS2Date      Unsigned32,
                    minInstPowerApparentS3          Unsigned32,
                    minInstPowerApparentS3Date      Unsigned32,
                --  10x ==> Power Factor Measurements
                    minInstPowerFactorPF1           Integer32, 
                    minInstPowerFactorTypeSPF1      Unsigned32,
                    minInstPowerFactorPF1Date       Unsigned32,
                    minInstPowerFactorPF2           Integer32,
                    minInstPowerFactorTypeSPF2      Unsigned32,
                    minInstPowerFactorPF2Date       Unsigned32,
                    minInstPowerFactorPF3           Integer32,
                    minInstPowerFactorTypeSPF3      Unsigned32,
                    minInstPowerFactorPF3Date       Unsigned32
                   }

    -- *******************************************************************************
    -- Definition of Product Metrology Max Averages Entry
    SeqMaxAveragesEnt ::= SEQUENCE {            
                   maxAvgModbusAddress         Unsigned32,
                   maxAvgProductIndex         Unsigned32,
                   maxAvgLoadIndex            Unsigned32,
                   maxAvgLoadRowStatus        RowStatus,
                -- 1x ==> System Measurements
                   maxAvgFrequency            Unsigned32,
                   maxAvgFrequencyDate        Unsigned32,
                -- 2x/3x ==> Voltage Measurements
                   maxAvgVoltPhNV1            Unsigned32,
                   maxAvgVoltPhNV1Date        Unsigned32,
                   maxAvgVoltPhNV2            Unsigned32,
                   maxAvgVoltPhNV2Date        Unsigned32,
                   maxAvgVoltPhNV3            Unsigned32,
                   maxAvgVoltPhNV3Date        Unsigned32,
                   maxAvgVoltPhNVn            Unsigned32,
                   maxAvgVoltPhNVnDate        Unsigned32,
                   maxAvgVoltPhPhU12          Unsigned32,
                   maxAvgVoltPhPhU12Date      Unsigned32,
                   maxAvgVoltPhPhU23          Unsigned32,
                   maxAvgVoltPhPhU23Date      Unsigned32,
                   maxAvgVoltPhPhU31          Unsigned32,
                   maxAvgVoltPhPhU31Date      Unsigned32,
                -- 4x/5x ==> Current Measurements
                   maxAvgCurrentI1            Unsigned32, 
                   maxAvgCurrentI1Date        Unsigned32,
                   maxAvgCurrentI2            Unsigned32, 
                   maxAvgCurrentI2Date        Unsigned32,
                   maxAvgCurrentI3            Unsigned32, 
                   maxAvgCurrentI3Date        Unsigned32, 
                   maxAvgCurrentIn            Unsigned32, 
                   maxAvgCurrentInDate        Unsigned32,
                -- 6x/7x ==> Total Power Measurements
                   maxAvgTotalPowerActive         Integer32,  
                   maxAvgTotalPowerActiveDate     Unsigned32,
                   maxAvgTotalPowerReactive       Integer32,
                   maxAvgTotalPowerReactiveDate   Unsigned32,
                   maxAvgTotalPowerApparent       Unsigned32, 
                   maxAvgTotalPowerApparentDate   Unsigned32,
                   maxAvgTotalPowerFactor         Integer32,
                   maxAvgTotalPowerFactorType     Unsigned32,
                   maxAvgTotalPowerFactorDate     Unsigned32,
                -- 8x/9x ==> Phasis Power Measurements
                   maxAvgPowerActiveP1        Integer32,
                   maxAvgPowerActiveP1Date    Unsigned32,
                   maxAvgPowerActiveP2        Integer32,
                   maxAvgPowerActiveP2Date    Unsigned32,
                   maxAvgPowerActiveP3        Integer32,
                   maxAvgPowerActiveP3Date    Unsigned32,
                   maxAvgPowerReactiveQ1      Integer32,
                   maxAvgPowerReactiveQ1Date  Unsigned32,
                   maxAvgPowerReactiveQ2      Integer32,
                   maxAvgPowerReactiveQ2Date  Unsigned32,
                   maxAvgPowerReactiveQ3      Integer32,
                   maxAvgPowerReactiveQ3Date  Unsigned32,
                   maxAvgPowerApparentS1      Unsigned32,
                   maxAvgPowerApparentS1Date  Unsigned32,
                   maxAvgPowerApparentS2      Unsigned32,
                   maxAvgPowerApparentS2Date  Unsigned32,
                   maxAvgPowerApparentS3      Unsigned32,
                   maxAvgPowerApparentS3Date  Unsigned32,
                -- 10x ==> Power Factor Measurements
                   maxAvgPowerFactorPF1       Integer32, 
                   maxAvgPowerFactorTypeSPF1  Unsigned32,
                   maxAvgPowerFactorPF1Date   Unsigned32, 
                   maxAvgPowerFactorPF2       Integer32, 
                   maxAvgPowerFactorTypeSPF2  Unsigned32,
                   maxAvgPowerFactorPF2Date   Unsigned32,
                   maxAvgPowerFactorPF3       Integer32,
                   maxAvgPowerFactorTypeSPF3  Unsigned32,
                   maxAvgPowerFactorPF3Date   Unsigned32
                   }

    -- *******************************************************************************
    -- Definition of Product Metrology Min Averages Entry
    SeqMinAveragesEnt ::= SEQUENCE {            
                   minAvgModbusAddress         Unsigned32,
                   minAvgProductIndex         Unsigned32,
                   minAvgLoadIndex            Unsigned32,
                   minAvgLoadRowStatus        RowStatus,
                -- 1x ==> System Measurements
                   minAvgFrequency            Unsigned32,
                   minAvgFrequencyDate        Unsigned32,
                -- 2x/3x ==> Voltage Measurements
                   minAvgVoltPhNV1            Unsigned32,
                   minAvgVoltPhNV1Date        Unsigned32,
                   minAvgVoltPhNV2            Unsigned32,
                   minAvgVoltPhNV2Date        Unsigned32,
                   minAvgVoltPhNV3            Unsigned32,
                   minAvgVoltPhNV3Date        Unsigned32,
                   minAvgVoltPhNVn            Unsigned32,
                   minAvgVoltPhNVnDate        Unsigned32,
                   minAvgVoltPhPhU12          Unsigned32,
                   minAvgVoltPhPhU12Date      Unsigned32,
                   minAvgVoltPhPhU23          Unsigned32,
                   minAvgVoltPhPhU23Date      Unsigned32,
                   minAvgVoltPhPhU31          Unsigned32,
                   minAvgVoltPhPhU31Date      Unsigned32,
                -- 4x/5x ==> Current Measurements
                   minAvgCurrentI1            Unsigned32, 
                   minAvgCurrentI1Date        Unsigned32,
                   minAvgCurrentI2            Unsigned32, 
                   minAvgCurrentI2Date        Unsigned32,
                   minAvgCurrentI3            Unsigned32, 
                   minAvgCurrentI3Date        Unsigned32, 
                   minAvgCurrentIn            Unsigned32, 
                   minAvgCurrentInDate        Unsigned32,
                -- 6x/7x ==> Total Power Measurements
                   minAvgTotalPowerActive         Integer32,  
                   minAvgTotalPowerActiveDate     Unsigned32,
                   minAvgTotalPowerReactive       Integer32,
                   minAvgTotalPowerReactiveDate   Unsigned32,
                   minAvgTotalPowerApparent       Unsigned32, 
                   minAvgTotalPowerApparentDate   Unsigned32,
                   minAvgTotalPowerFactor         Integer32,
                   minAvgTotalPowerFactorType     Unsigned32,
                   minAvgTotalPowerFactorDate     Unsigned32,
                -- 8x/9x ==> Phasis Power Measurements
                   minAvgPowerActiveP1        Integer32,
                   minAvgPowerActiveP1Date    Unsigned32,
                   minAvgPowerActiveP2        Integer32,
                   minAvgPowerActiveP2Date    Unsigned32,
                   minAvgPowerActiveP3        Integer32,
                   minAvgPowerActiveP3Date    Unsigned32,
                   minAvgPowerReactiveQ1      Integer32,
                   minAvgPowerReactiveQ1Date  Unsigned32,
                   minAvgPowerReactiveQ2      Integer32,
                   minAvgPowerReactiveQ2Date  Unsigned32,
                   minAvgPowerReactiveQ3      Integer32,
                   minAvgPowerReactiveQ3Date  Unsigned32,
                   minAvgPowerApparentS1      Unsigned32,
                   minAvgPowerApparentS1Date  Unsigned32,
                   minAvgPowerApparentS2      Unsigned32,
                   minAvgPowerApparentS2Date  Unsigned32,
                   minAvgPowerApparentS3      Unsigned32,
                   minAvgPowerApparentS3Date  Unsigned32,
                -- 10x ==> Power Factor Measurements
                   minAvgPowerFactorPF1       Integer32, 
                   minAvgPowerFactorTypeSPF1  Unsigned32,
                   minAvgPowerFactorPF1Date   Unsigned32, 
                   minAvgPowerFactorPF2       Integer32, 
                   minAvgPowerFactorTypeSPF2  Unsigned32,
                   minAvgPowerFactorPF2Date   Unsigned32,
                   minAvgPowerFactorPF3       Integer32,
                   minAvgPowerFactorTypeSPF3  Unsigned32,
                   minAvgPowerFactorPF3Date   Unsigned32
                   }

    -- *******************************************************************************

    -- Definition of Product Measurement Instantaneous THD Entry
    SeqInstantaneousCurrentTHDEnt ::= SEQUENCE {            
                   instCurrentTHDModbusAddress        Unsigned32,
                   instCurrentTHDProductIndex        Unsigned32,
                   instCurrentTHDLoadIndex           Unsigned32,
                   instCurrentTHDLoadRowStatus       RowStatus,
                -- Instantaneous THD
                   instTHDI1                         Unsigned32,
                   instTHDI2                         Unsigned32,
                   instTHDI3                         Unsigned32,
                   instTHDIn                         Unsigned32,
                -- Maximum THD
                   instMaxTHDI1                      Unsigned32,
                   instMaxTHDI1Date                  Unsigned32,
                   instMaxTHDI2                      Unsigned32,
                   instMaxTHDI2Date                  Unsigned32,
                   instMaxTHDI3                      Unsigned32,
                   instMaxTHDI3Date                  Unsigned32,
                   instMaxTHDIn                      Unsigned32,
                   instMaxTHDInDate                  Unsigned32,   
                -- Minimum THD
                   instMinTHDI1                      Unsigned32,
                   instMinTHDI1Date                  Unsigned32,
                   instMinTHDI2                      Unsigned32,
                   instMinTHDI2Date                  Unsigned32,
                   instMinTHDI3                      Unsigned32,
                   instMinTHDI3Date                  Unsigned32,
                   instMinTHDIn                      Unsigned32,
                   instMinTHDInDate                  Unsigned32
                   }

    SeqInstantaneousVoltageTHDEnt ::= SEQUENCE {            
                   instVoltageTHDModbusAddress        Unsigned32,
                   instVoltageTHDProductIndex        Unsigned32,
                   instVoltageTHDLoadRowStatus       RowStatus,
                -- Instantaneous THD
                   instTHDV1                         Unsigned32,
                   instTHDV2                         Unsigned32,
                   instTHDV3                         Unsigned32,
                   instTHDU12                        Unsigned32,
                   instTHDU23                        Unsigned32,
                   instTHDU31                        Unsigned32,
                -- Maximum THD
                   instMaxTHDV1                      Unsigned32,
                   instMaxTHDV1Date                  Unsigned32,
                   instMaxTHDV2                      Unsigned32,
                   instMaxTHDV2Date                  Unsigned32,
                   instMaxTHDV3                      Unsigned32,
                   instMaxTHDV3Date                  Unsigned32,
                   instMaxTHDU12                     Unsigned32,
                   instMaxTHDU12Date                 Unsigned32,
                   instMaxTHDU23                     Unsigned32,
                   instMaxTHDU23Date                 Unsigned32,
                   instMaxTHDU31                     Unsigned32,
                   instMaxTHDU31Date                 Unsigned32,
                -- Minimum THD
                   instMinTHDV1                      Unsigned32,
                   instMinTHDV1Date                  Unsigned32,
                   instMinTHDV2                      Unsigned32,
                   instMinTHDV2Date                  Unsigned32,
                   instMinTHDV3                      Unsigned32,
                   instMinTHDV3Date                  Unsigned32,
                   instMinTHDU12                     Unsigned32,
                   instMinTHDU12Date                 Unsigned32,
                   instMinTHDU23                     Unsigned32,
                   instMinTHDU23Date                 Unsigned32,
                   instMinTHDU31                     Unsigned32,
                   instMinTHDU31Date                 Unsigned32
                   }

    -- Definition of Product Measurement Instantaneous Current Harmonics Entry
    SeqInstantaneousCurrentHarmonicsEnt ::= SEQUENCE {            
                   instCurrentHarmonicsModbusAddress        Unsigned32,
                   instCurrentHarmonicsProductIndex  Unsigned32,
                   instCurrentHarmonicsLoadIndex     Unsigned32,
                   instCurrentHarmonicsLoadRowStatus RowStatus,
                -- Harmonics Row for I1
                   instHarmonicsRow02I1              Unsigned32,
                   instHarmonicsRow03I1              Unsigned32,
                   instHarmonicsRow04I1              Unsigned32,
                   instHarmonicsRow05I1              Unsigned32,
                   instHarmonicsRow06I1              Unsigned32,
                   instHarmonicsRow07I1              Unsigned32,
                   instHarmonicsRow08I1              Unsigned32,
                   instHarmonicsRow09I1              Unsigned32,
                   instHarmonicsRow10I1              Unsigned32,
                -- Harmonics Row for I2
                   instHarmonicsRow02I2              Unsigned32,
                   instHarmonicsRow03I2              Unsigned32,
                   instHarmonicsRow04I2              Unsigned32,
                   instHarmonicsRow05I2              Unsigned32,
                   instHarmonicsRow06I2              Unsigned32,
                   instHarmonicsRow07I2              Unsigned32,
                   instHarmonicsRow08I2              Unsigned32,
                   instHarmonicsRow09I2              Unsigned32,
                   instHarmonicsRow10I2              Unsigned32,
                -- Harmonics Row for I3
                   instHarmonicsRow02I3              Unsigned32,
                   instHarmonicsRow03I3              Unsigned32,
                   instHarmonicsRow04I3              Unsigned32,
                   instHarmonicsRow05I3              Unsigned32,
                   instHarmonicsRow06I3              Unsigned32,
                   instHarmonicsRow07I3              Unsigned32,
                   instHarmonicsRow08I3              Unsigned32,
                   instHarmonicsRow09I3              Unsigned32,
                   instHarmonicsRow10I3              Unsigned32,
                -- Harmonics Row for In
                   instHarmonicsRow02In              Unsigned32,
                   instHarmonicsRow03In              Unsigned32,
                   instHarmonicsRow04In              Unsigned32,
                   instHarmonicsRow05In              Unsigned32,
                   instHarmonicsRow06In              Unsigned32,
                   instHarmonicsRow07In              Unsigned32,
                   instHarmonicsRow08In              Unsigned32,
                   instHarmonicsRow09In              Unsigned32,
                   instHarmonicsRow10In              Unsigned32
                   }

    -- Definition of Product Measurement Instantaneous Voltage Phase-Neutral Harmonics Entry
    SeqInstantaneousVoltagePhNHarmonicsEnt ::= SEQUENCE {            
                   instVoltagePhNHarmonicsModbusAddress        Unsigned32,
                   instVoltagePhNHarmonicsProductIndex   Unsigned32,
                   instVoltagePhNHarmonicsLoadRowStatus  RowStatus,
                -- Harmonics Row for V1
                   instHarmonicsRow02V1              Unsigned32,
                   instHarmonicsRow03V1              Unsigned32,
                   instHarmonicsRow04V1              Unsigned32,
                   instHarmonicsRow05V1              Unsigned32,
                   instHarmonicsRow06V1              Unsigned32,
                   instHarmonicsRow07V1              Unsigned32,
                   instHarmonicsRow08V1              Unsigned32,
                   instHarmonicsRow09V1              Unsigned32,
                   instHarmonicsRow10V1              Unsigned32,
                -- Harmonics Row for V2
                   instHarmonicsRow02V2              Unsigned32,
                   instHarmonicsRow03V2              Unsigned32,
                   instHarmonicsRow04V2              Unsigned32,
                   instHarmonicsRow05V2              Unsigned32,
                   instHarmonicsRow06V2              Unsigned32,
                   instHarmonicsRow07V2              Unsigned32,
                   instHarmonicsRow08V2              Unsigned32,
                   instHarmonicsRow09V2              Unsigned32,
                   instHarmonicsRow10V2              Unsigned32,
                -- Harmonics Row for V3
                   instHarmonicsRow02V3              Unsigned32,
                   instHarmonicsRow03V3              Unsigned32,
                   instHarmonicsRow04V3              Unsigned32,
                   instHarmonicsRow05V3              Unsigned32,
                   instHarmonicsRow06V3              Unsigned32,
                   instHarmonicsRow07V3              Unsigned32,
                   instHarmonicsRow08V3              Unsigned32,
                   instHarmonicsRow09V3              Unsigned32,
                   instHarmonicsRow10V3              Unsigned32
                   }

    -- Definition of Product Measurement Instantaneous Voltage Phase-Phase Harmonics Entry
    SeqInstantaneousVoltagePhPhHarmonicsEnt ::= SEQUENCE {            
                   instVoltagePhPhHarmonicsModbusAddress        Unsigned32,
                   instVoltagePhPhHarmonicsProductIndex   Unsigned32,
                   instVoltagePhPhHarmonicsLoadRowStatus  RowStatus,
                -- Harmonics Row for U12
                   instHarmonicsRow02U12             Unsigned32,
                   instHarmonicsRow03U12             Unsigned32,
                   instHarmonicsRow04U12             Unsigned32,
                   instHarmonicsRow05U12             Unsigned32,
                   instHarmonicsRow06U12             Unsigned32,
                   instHarmonicsRow07U12             Unsigned32,
                   instHarmonicsRow08U12             Unsigned32,
                   instHarmonicsRow09U12             Unsigned32,
                   instHarmonicsRow10U12             Unsigned32,
                -- Harmonics Row for U23
                   instHarmonicsRow02U23             Unsigned32,
                   instHarmonicsRow03U23             Unsigned32,
                   instHarmonicsRow04U23             Unsigned32,
                   instHarmonicsRow05U23             Unsigned32,
                   instHarmonicsRow06U23             Unsigned32,
                   instHarmonicsRow07U23             Unsigned32,
                   instHarmonicsRow08U23             Unsigned32,
                   instHarmonicsRow09U23             Unsigned32,
                   instHarmonicsRow10U23             Unsigned32,
                -- Harmonics Row for U31
                   instHarmonicsRow02U31             Unsigned32,
                   instHarmonicsRow03U31             Unsigned32,
                   instHarmonicsRow04U31             Unsigned32,
                   instHarmonicsRow05U31             Unsigned32,
                   instHarmonicsRow06U31             Unsigned32,
                   instHarmonicsRow07U31             Unsigned32,
                   instHarmonicsRow08U31             Unsigned32,
                   instHarmonicsRow09U31             Unsigned32,
                   instHarmonicsRow10U31             Unsigned32
                   }


    -- *******************************************************************************
    -- Definition of Product Digital Input Entry
    SeqDigInputEnt ::= SEQUENCE {            
                    inputDigitalModbusAddress       Unsigned32,
                    inputDigitalProductIndex        Unsigned32,
                    inputDigitalLineIndex           Unsigned32,
                    inputDigitalRowStatus           RowStatus,
                    inputDigitalFunction            SocomecIOFunctions,
                    inputDigitalActivated           Unsigned32,
                    inputDigitalMode                SocomecModeDigitalIO
                 }

    -- Definition of Product Digital Output Entry
    SeqDigOutputEnt ::= SEQUENCE {            
                    outputDigitalModbusAddress      Unsigned32,
                    outputDigitalProductIndex       Unsigned32,
                    outputDigitalLineIndex          Unsigned32,
                    outputDigitalRowStatus          RowStatus,
                    outputDigitalFunction           SocomecIOFunctions,
                    outputDigitalActivated          Unsigned32,
                    outputDigitalMode               SocomecModeDigitalIO,
                    outputDigitalCmdDeact           Unsigned32,
                    outputDigitalCmdAct             Unsigned32
                 }

    -- Definition of Product Protection Table
    SeqProtectionEnt ::= SEQUENCE {
                    protectionModbusAddress            Unsigned32,
                    protectionProductIndex             Unsigned32,
                    protectionProtectIndex             Unsigned32,
                    protectionRowStatus                RowStatus,
                    protectionPosition                 SocomecBreakerPosition,
                    protectionTripStatus               SocomecTripStatus,
                    protectionPole1Position            SocomecBreakerPosition,
                    protectionPole2Position            SocomecBreakerPosition,
                    protectionPole3Position            SocomecBreakerPosition,
                    protectionDefectiveDeviceStatus    SocomecBreakerFault,
                    protectionTripCause                SocomecTripCause,
                    protectionRCDDeviceFault           SocomecBreakerFault,
                    protectionTotalCount               Unsigned32,
                    protectionLowLoadOperationCount    Unsigned32,
                    protectionOnLoadOperationCount     Unsigned32,
                    protectionOverLoadOperationCount   Unsigned32,
                    protectionTripCount                Unsigned32,
                    protectionLastTripDate             Unsigned32
                 } 
		
    SeqAnaInputEnt ::= SEQUENCE {            
                    inputAnalogModbusAddress        Unsigned32,
                    inputAnalogProductIndex         Unsigned32,
                    inputAnalogLineIndex            Unsigned32,
                    inputAnalogRowStatus            RowStatus,
                    inputAnalogPresentValue         Integer32,
                    inputAnalogAverageValue         Integer32,
                    inputAnalogUnit                 DisplayString,
                    inputAnalogMode                 SocomecModeAnalogIO
                 }

    SeqAnaOutputEnt ::= SEQUENCE {            
                    outputAnalogModbusAddress       Unsigned32,
                    outputAnalogProductIndex        Unsigned32,
                    outputAnalogLineIndex           Unsigned32,
                    outputAnalogRowStatus           RowStatus,
                    outputAnalogVariableService     Unsigned32,
                    outputAnalogVariableInstance    Unsigned32,
                    outputAnalogMode                SocomecModeAnalogIO
                 }

    SeqAlmInProgressEnt ::= SEQUENCE {            
                    almInProgressAlarmIndex        SocomecAlarmType,
                    almInProgressAlarmNumber       Unsigned32,
                    almInProgressRowStatus         RowStatus
                 }
                 
    -- *******************************************************************************

    -- Definition of Metrology DC Entry
    SeqMetroDCEnt ::= SEQUENCE {            
                   dcModbusAddress                  Unsigned32 ,
                   dcProductIndex                   Unsigned32 ,
                   dcLoadIndex                      Unsigned32 ,
                   dcLoadRowStatus                  RowStatus  ,
    
				   dcInstIrms                       Unsigned32 ,
                   dcInstIdc                        Integer32  ,
                   dcInstIripple                    Unsigned32 ,
				   dcAvgIrms                        Unsigned32 ,
                   dcAvgIdc                         Integer32  ,
                   dcAvgIripple                     Unsigned32 ,
    
				   dcMaxInstIrms                    Unsigned32 ,
				   dcMaxInstIrmsDate                Unsigned32 ,
                   dcMaxInstIdc                     Integer32  ,
                   dcMaxInstIdcDate                 Unsigned32 ,
                   dcMaxInstIripple                 Unsigned32 ,
                   dcMaxInstIrippleDate             Unsigned32 ,
				   dcMinInstIrms                    Unsigned32 ,
				   dcMinInstIrmsDate                Unsigned32 ,
                   dcMinInstIdc                     Integer32  ,
                   dcMinInstIdcDate                 Unsigned32 ,
                   dcMinInstIripple                 Unsigned32 ,
                   dcMinInstIrippleDate             Unsigned32 ,
				   dcMaxAvgIrms                     Unsigned32 ,
				   dcMaxAvgIrmsDate                 Unsigned32 ,
                   dcMaxAvgIdc                      Integer32  ,
                   dcMaxAvgIdcDate                  Unsigned32 ,
                   dcMaxAvgIripple                  Unsigned32 ,
                   dcMaxAvgIrippleDate              Unsigned32 ,
				   dcMinAvgIrms                     Unsigned32 ,
				   dcMinAvgIrmsDate                 Unsigned32 ,
                   dcMinAvgIdc                      Integer32  ,
                   dcMinAvgIdcDate                  Unsigned32 ,
                   dcMinAvgIripple                  Unsigned32 ,
                   dcMinAvgIrippleDate              Unsigned32 ,
    
                   dcAvgDateLastInstance            Unsigned32 ,
    
                   dcInstTotalPowerActive           Integer32  ,
                   dcAvgTotalPowerActive            Integer32  ,
                   dcMinInstTotalPowerActive        Integer32  ,
                   dcMinInstTotalPowerActiveDate    Unsigned32 ,
                   dcMaxInstTotalPowerActive        Integer32  ,
                   dcMaxInstTotalPowerActiveDate    Unsigned32 ,
                   dcMinAvgTotalPowerActive         Integer32  ,
                   dcMinAvgTotalPowerActiveDate     Unsigned32 ,
                   dcMaxAvgTotalPowerActive         Integer32  ,
                   dcMaxAvgTotalPowerActiveDate     Unsigned32 ,
    
				   dcInstVrms                       Unsigned32 ,
                   dcInstVdc                        Integer32  ,
                   dcInstVripple                    Unsigned32 ,
				   dcAvgVrms                        Unsigned32 ,
                   dcAvgVdc                         Integer32  ,
                   dcAvgVripple                     Unsigned32 ,
    
				   dcMaxInstVrms                    Unsigned32 ,
				   dcMaxInstVrmsDate                Unsigned32 ,
                   dcMaxInstVdc                     Integer32  ,
                   dcMaxInstVdcDate                 Unsigned32 ,
                   dcMaxInstVripple                 Unsigned32 ,
                   dcMaxInstVrippleDate             Unsigned32 ,
				   dcMinInstVrms                    Unsigned32 ,
				   dcMinInstVrmsDate                Unsigned32 ,
                   dcMinInstVdc                     Integer32  ,
                   dcMinInstVdcDate                 Unsigned32 ,
                   dcMinInstVripple                 Unsigned32 ,
                   dcMinInstVrippleDate             Unsigned32 ,
				   dcMaxAvgVrms                     Unsigned32 ,
				   dcMaxAvgVrmsDate                 Unsigned32 ,
                   dcMaxAvgVdc                      Integer32  ,
                   dcMaxAvgVdcDate                  Unsigned32 ,
                   dcMaxAvgVripple                  Unsigned32 ,
                   dcMaxAvgVrippleDate              Unsigned32 ,
				   dcMinAvgVrms                     Unsigned32 ,
				   dcMinAvgVrmsDate                 Unsigned32 ,
                   dcMinAvgVdc                      Integer32  ,
                   dcMinAvgVdcDate                  Unsigned32 ,
                   dcMinAvgVripple                  Unsigned32 ,
                   dcMinAvgVrippleDate              Unsigned32 
                   }

    -- *******************************************************************************

    -- Definition of Product Ats Mesurement Table Entry (Old table)
    SeqAtsMetroLegacyEnt ::= SEQUENCE {            
                    atsMetroLegacyModbusAddress              Unsigned32,
                    atsMetroLegacyProductIndex               Unsigned32,
                    atsMetroLegacyRowStatus                  RowStatus,
					
                    atsMetroLegacyVoltPhPhU12Source1         Unsigned32,
                    atsMetroLegacyVoltPhPhU23Source1         Unsigned32,
                    atsMetroLegacyVoltPhPhU31Source1         Unsigned32,
                    atsMetroLegacyVoltPhNV1Source1           Unsigned32,
                    atsMetroLegacyVoltPhNV2Source1           Unsigned32,
                    atsMetroLegacyVoltPhNV3Source1           Unsigned32,
                    atsMetroLegacyFrequencySource1           Unsigned32,
                    atsMetroLegacyVoltPhPhU12Source2         Unsigned32,
                    atsMetroLegacyVoltPhPhU23Source2         Unsigned32,
                    atsMetroLegacyVoltPhPhU31Source2         Unsigned32,
                    atsMetroLegacyVoltPhNV1Source2           Unsigned32,
                    atsMetroLegacyVoltPhNV2Source2           Unsigned32,
                    atsMetroLegacyVoltPhNV3Source2           Unsigned32,
                    atsMetroLegacyFrequencySource2           Unsigned32
                 }

    -- Definition of Product Ats Mesurement Table Entry
    SeqAtsMetroEnt ::= SEQUENCE {            
                    atsMetroModbusAddress              Unsigned32,
                    atsMetroProductIndex               Unsigned32,
					atsMetroSourceIndex                Unsigned32,
                    atsMetroRowStatus                  RowStatus,
					
                    atsMetroVoltPhPhU12Source          Unsigned32,
                    atsMetroVoltPhPhU23Source          Unsigned32,
                    atsMetroVoltPhPhU31Source          Unsigned32,
                    atsMetroVoltPhNV1Source            Unsigned32,
                    atsMetroVoltPhNV2Source            Unsigned32,
                    atsMetroVoltPhNV3Source            Unsigned32,
                    atsMetroFrequencySource            Unsigned32
                 }

    -- Definition of Product Ats Status Entry
    SeqAtsStatusEnt ::= SEQUENCE {            
                    atsStatusModbusAddress             Unsigned32,
                    atsStatusProductIndex              Unsigned32,
                    atsStatusRowStatus                 RowStatus,
					
                    atsStatusSourcePrio                SocomecAtsSourcePrio,
                    atsStatusSwitchAlarmFaultCode      SocomecAtsAlarmFault,
                    atsStatusSwitchOperatingMode       SocomecAtsOperatingMode,
                    atsStatusSwitchPosition            SocomecAtsPosition,
                    atsStatusRelayStateSource1         Unsigned32,
                    atsStatusRelayStateSource2         Unsigned32,
                    atsStatusSwitchStateSource1        SocomecAtsStateSource,
                    atsStatusSwitchStateSource2        SocomecAtsStateSource,
                    atsStatusSwitchTestInProgress      SocomecAtsTestInProgress,
                    atsStatusCycleCounter              Unsigned32,
                    atsStatusOperationCounterPos1      Unsigned32,
                    atsStatusOperationCounterPos2      Unsigned32,
                    atsStatusSwitchFaultSummary        SocomecAtsSwitchFaultSummary,
                    atsStatusSwitchLastCause           SocomecAtsSwitchLastCause
                 }

    -- Definition of Product Command Table Entry (Old table)
    SeqProductCommandEnt ::= SEQUENCE {
                    commandModbusAddress              Unsigned32,
                    commandLineIndex                  Unsigned32,
                    commandRowStatus                  RowStatus,
                    commandProductIndex                  Unsigned32,

                    commandAtsGensetStartOrder        Unsigned32,
                    commandAtsPosition                Unsigned32,
                    commandAtsPriorityMode            Unsigned32,
                    commandAtsOperatingMode           Unsigned32,
                    commandAtsCommandAlarm            Unsigned32
                 }


socomec-diris-products-MIB MODULE-IDENTITY
    LAST-UPDATED "202408211200Z"
    ORGANIZATION "Socomec Software"
    CONTACT-INFO "SOCOMEC"
    DESCRIPTION  "MIB Definition for Socomec Diris Products"

    REVISION    "202408211200Z"
    DESCRIPTION  "Added Circuit Table"
    REVISION    "201903261200Z"
    DESCRIPTION  "Added Command Chapter"
    REVISION    "201902011200Z"
    DESCRIPTION "Added New ATS metro table"
    REVISION    "201706271200Z"
    DESCRIPTION "Added DC Metrology"
    REVISION    "201706161200Z"
    DESCRIPTION "Added ATS Tables"
    REVISION    "201606081200Z"
    DESCRIPTION "Initial Version"
    ::= { socomecModules 10 }

    socomec               OBJECT IDENTIFIER ::= { enterprises 4555 }
    socomecProducts       OBJECT IDENTIFIER ::= { socomec 10 }
    socomecModules        OBJECT IDENTIFIER ::= { socomec 80 }
    socomecMIBConformance OBJECT IDENTIFIER ::= { socomec 90 }
    productIdentification OBJECT IDENTIFIER ::= { socomecProducts 10 }
    productMetrology      OBJECT IDENTIFIER ::= { socomecProducts 20 }
    productStates         OBJECT IDENTIFIER ::= { socomecProducts 30 }
    productCommand        OBJECT IDENTIFIER ::= { socomecProducts 80 }
    productTraps          OBJECT IDENTIFIER ::= { socomecProducts 90 }
    productAts            OBJECT IDENTIFIER ::= { socomecProducts 40 }
    
	
	

-- *******************************************************************************
-- ********************* PRODUCT IDENTIFICATION TABLE ****************************
identificationTable    OBJECT-TYPE
                SYNTAX      SEQUENCE OF SeqIdentificationEnt
                MAX-ACCESS  not-accessible
                STATUS      current
                DESCRIPTION "Product identification Table"
                ::= { productIdentification 10 }

identificationEntry    OBJECT-TYPE
                SYNTAX      SeqIdentificationEnt
                MAX-ACCESS  not-accessible
                STATUS      current
                DESCRIPTION "Identification Table for given Product Index"
                INDEX  { identModbusAddress }
                ::= { identificationTable 1 }

identModbusAddress    OBJECT-TYPE
                SYNTAX      Unsigned32(1..255)
                MAX-ACCESS  read-only
                STATUS      current
                DESCRIPTION "Modbus address of the product"
                ::= { identificationEntry 1 }
				
identProductIndex    OBJECT-TYPE
                SYNTAX      Unsigned32(1..33)  -- 32 Products + 1 Gateway
                MAX-ACCESS  read-only
                STATUS      current
                DESCRIPTION "Index of the Product to reach (1 = Gateway itself)"
                ::= { identificationEntry 5 }

identProductRowStatus   OBJECT-TYPE
                SYNTAX       RowStatus
                MAX-ACCESS   read-only
                STATUS       current
                DESCRIPTION "The status of this conceptual row."
                ::= { identificationEntry 10 }
				
identTypeProduct    OBJECT-TYPE
                SYNTAX      Unsigned32
                MAX-ACCESS  read-only
                STATUS      current
                DESCRIPTION "Type of the Product"
                ::= { identificationEntry 55002 }
				
identType       OBJECT-TYPE
                SYNTAX      DisplayString (SIZE (0..255))
                MAX-ACCESS  read-only
                STATUS      current
                DESCRIPTION "A textual description of the type of the Product"
                ::= { identificationEntry 55003 }
    
identSWVersion OBJECT-TYPE
                SYNTAX      DisplayString (SIZE (0..255))
                MAX-ACCESS  read-only
                STATUS      current
                DESCRIPTION "Software Version Major.Minor.Revision.Build (MM.mm.rr.bb)"
                ::= { identificationEntry 55000 }
    
--identVersionMajor      OBJECT-TYPE                           --
--                SYNTAX      Unsigned32                       --
--                MAX-ACCESS  read-only                        --
--                STATUS      current                          --
--                DESCRIPTION "Product Version (Major)"        --
--                ::= { identificationEntry 55008 }            --
--                                                             --
--identVersionMinor      OBJECT-TYPE                           --
--                SYNTAX      Unsigned32                       --
--                MAX-ACCESS  read-only                        --
--                STATUS      current                          --
--                DESCRIPTION "Product Version (Minor)"        --
--                ::= { identificationEntry 55009 }            --
--                                                             --
--identVersionRevision   OBJECT-TYPE                           --
--                SYNTAX      Unsigned32                       --
--                MAX-ACCESS  read-only                        --
--                STATUS      current                          --
--                DESCRIPTION "Product Version (Revision)"     --
--                ::= { identificationEntry 55010 }            --
--                                                             --
--identVersionBuild   OBJECT-TYPE                              --
--                SYNTAX      Unsigned32                       --
--                MAX-ACCESS  read-only                        --
--                STATUS      current                          --
--                DESCRIPTION "Product Version (Build)"        --
--                ::= { identificationEntry 55011 }            --
--                                                             --
identVersionBuildDate   OBJECT-TYPE
                SYNTAX      DisplayString (SIZE (0..255))
                MAX-ACCESS  read-only
                STATUS      current
                DESCRIPTION "Product Build Date"
                ::= { identificationEntry 55012 }
                
identSerialAASS   OBJECT-TYPE
                SYNTAX      Unsigned32
                MAX-ACCESS  read-only
                STATUS      current
                DESCRIPTION "Product Serial AA SS"
                ::= { identificationEntry 55004 }
                
identSerialSSTL   OBJECT-TYPE
                SYNTAX      Unsigned32
                MAX-ACCESS  read-only
                STATUS      current
                DESCRIPTION "Product Serial SST L"
                ::= { identificationEntry 55005 }
                
identSerialOrder   OBJECT-TYPE
                SYNTAX      Unsigned32
                MAX-ACCESS  read-only
                STATUS      current
                DESCRIPTION "Product Serial Order"
                ::= { identificationEntry 55006 }
                
identSerialReserve   OBJECT-TYPE
                SYNTAX      Unsigned32
                MAX-ACCESS  read-only
                STATUS      current
                DESCRIPTION "Product Serial Reserve"
                ::= { identificationEntry 55007 }

identOperatingCounter   OBJECT-TYPE
                SYNTAX      Unsigned32
                MAX-ACCESS  read-only
                STATUS      current
                DESCRIPTION "Product Operating Hour counter"
                ::= { identificationEntry 65535 }

-- *******************************************************************************
-- ********************* PRODUCT IDENTIFICATION TABLE ****************************
circuitTable    OBJECT-TYPE
                SYNTAX      SEQUENCE OF SeqCircuitEnt
                MAX-ACCESS  not-accessible
                STATUS      current
                DESCRIPTION "Circuit identification Table"
                ::= { productIdentification 20 }

circuitEntry    OBJECT-TYPE
                SYNTAX      SeqCircuitEnt
                MAX-ACCESS  not-accessible
                STATUS      current
                DESCRIPTION "Circuit identification Table for a given Product and Load Index"
                INDEX  { circuitProductModbusAddress, circuitProductLine }
                ::= { circuitTable 1 }

circuitIndex    OBJECT-TYPE
                SYNTAX      Unsigned32(1..192)
                MAX-ACCESS  read-only
                STATUS      current
                DESCRIPTION "Index of the Circuit in the System"
                ::= { circuitEntry 5 }

circuitProductIndex    OBJECT-TYPE
                SYNTAX      Unsigned32(1..33)
                MAX-ACCESS  read-only
                STATUS      current
                DESCRIPTION "Index of the Product (meter)"
                ::= { circuitEntry 6 }

circuitProductLine    OBJECT-TYPE
                SYNTAX      Unsigned32(1..24)
                MAX-ACCESS  read-only
                STATUS      current
                DESCRIPTION "Index of the Circuit in the Meter"
                ::= { circuitEntry 7 }

circuitProductModbusAddress    OBJECT-TYPE
                SYNTAX      Unsigned32(1..255)
                MAX-ACCESS  read-only
                STATUS      current
                DESCRIPTION "Modbus address of the product"
                ::= { circuitEntry 8 }

circuitRowStatus OBJECT-TYPE
                SYNTAX       RowStatus
                MAX-ACCESS   read-only
                STATUS       current
                DESCRIPTION "The status of this conceptual row."
                ::= { circuitEntry 10 }

circuitName     OBJECT-TYPE
                SYNTAX      DisplayString (SIZE (0..255))
                MAX-ACCESS  read-only
                STATUS      current
                DESCRIPTION "Circuit Name"
                ::= { circuitEntry 85054 }

circuitType     OBJECT-TYPE
                SYNTAX      SocomecCircuitType
                MAX-ACCESS  read-only
                STATUS      current
                DESCRIPTION "Circuit type"
                ::= { circuitEntry 85013 }

circuitUsage    OBJECT-TYPE
                SYNTAX      SocomecCircuitUsage
                MAX-ACCESS  read-only
                STATUS      current
                DESCRIPTION "Circuit Usage"
                ::= { circuitEntry 85135 }

circuitNature   OBJECT-TYPE
                SYNTAX      SocomecCircuitNature
                MAX-ACCESS  read-only
                STATUS      current
                DESCRIPTION "Circuit Nature"
                ::= { circuitEntry 85136 }

circuitLocation OBJECT-TYPE
                SYNTAX      DisplayString (SIZE (0..255))
                MAX-ACCESS  read-only
                STATUS      current
                DESCRIPTION "Circuit location"
                ::= { circuitEntry 86000 }


-- *******************************************************************************
-- ********************* LOAD CURVES TABLE ***************************************
loadCurvesTable       OBJECT-TYPE
                SYNTAX      SEQUENCE OF SeqLoadCurvesEnt
                MAX-ACCESS  not-accessible
                STATUS      current
                DESCRIPTION "Load Curves metrology Table"
                ::= { productMetrology 10 }

loadCurvesEntry       OBJECT-TYPE
                SYNTAX      SeqLoadCurvesEnt
                MAX-ACCESS  not-accessible
                STATUS      current
                DESCRIPTION "Load Curves Data Table for given Product Index and Load Index"
                INDEX  { loadCurvesModbusAddress, loadCurvesLoadIndex  }
                ::= { loadCurvesTable 1 }

loadCurvesModbusAddress    OBJECT-TYPE
                SYNTAX      Unsigned32(1..255)
                MAX-ACCESS  read-only
                STATUS      current
                DESCRIPTION "Modbus address of the product"
                ::= { loadCurvesEntry 1 }

loadCurvesProductIndex    OBJECT-TYPE
                SYNTAX      Unsigned32(1..33)  -- 32 Products + 1 Gateway
                MAX-ACCESS  read-only
                STATUS      current
                DESCRIPTION "Index of the Product to reach (1 = Gateway itself)"
                ::= { loadCurvesEntry 5 }

loadCurvesLoadIndex       OBJECT-TYPE
                SYNTAX      Unsigned32 (1..16)  -- 6 Loads + 10 MultiFluids
                MAX-ACCESS  read-only
                STATUS      current
                DESCRIPTION "Index of the Load to reach"
                ::= { loadCurvesEntry 6 }

loadCurvesLoadRowStatus      OBJECT-TYPE
                SYNTAX       RowStatus
                MAX-ACCESS   read-create
                STATUS       current
                DESCRIPTION "The status of this conceptual row."
                ::= { loadCurvesEntry 10 }

loadCurvesActivePowerPos   OBJECT-TYPE
                SYNTAX      Unsigned32
                MAX-ACCESS  read-only
                STATUS      current
                DESCRIPTION "Last measured P10 Active Power Positive (W)"
                ::= { loadCurvesEntry 30100 }  
                
loadCurvesActivePowerNeg   OBJECT-TYPE
                SYNTAX      Unsigned32
                MAX-ACCESS  read-only
                STATUS      current
                DESCRIPTION "Last measured P10 Active Power Negative (W)"
                ::= { loadCurvesEntry 30101 }    
                
loadCurvesReactivePowerPos   OBJECT-TYPE
                SYNTAX      Unsigned32
                MAX-ACCESS  read-only
                STATUS      current
                DESCRIPTION "Last measured P10 Reactive Power Positive (var)"
                ::= { loadCurvesEntry 30102 }    
                
loadCurvesReactivePowerNeg   OBJECT-TYPE
                SYNTAX      Unsigned32
                MAX-ACCESS  read-only
                STATUS      current
                DESCRIPTION "Last measured P10 Reactive Power Negative (var)"
                ::= { loadCurvesEntry 30103 }    
                
loadCurvesApparentPower   OBJECT-TYPE
                SYNTAX      Unsigned32
                MAX-ACCESS  read-only
                STATUS      current
                DESCRIPTION "Last measured P10 Apparent Power (VA)"
                ::= { loadCurvesEntry 30104 }

-- *******************************************************************************
-- ********************* ENERGIES TABLE ******************************************
energyTable       OBJECT-TYPE
                SYNTAX      SEQUENCE OF SeqEnergyEnt
                MAX-ACCESS  not-accessible
                STATUS      current
                DESCRIPTION "Energies metrology Table"
                ::= { productMetrology 12 }

energyEntry       OBJECT-TYPE
                SYNTAX      SeqEnergyEnt
                MAX-ACCESS  not-accessible
                STATUS      current
                DESCRIPTION "Energies Data Table for given Product Index and Load Index"
                INDEX  { engModbusAddress, engLoadIndex  }
                ::= { energyTable 1 }

engModbusAddress    OBJECT-TYPE
                SYNTAX      Unsigned32(1..255)
                MAX-ACCESS  read-only
                STATUS      current
                DESCRIPTION "Modbus address of the product"
                ::= { energyEntry 1 }

engProductIndex    OBJECT-TYPE
                SYNTAX      Unsigned32(1..33)  -- 32 Products + 1 Gateway
                MAX-ACCESS  read-only
                STATUS      current
                DESCRIPTION "Index of the Product to reach (1 = Gateway itself)"
                ::= { energyEntry 5 }

engLoadIndex       OBJECT-TYPE
                SYNTAX      Unsigned32 (1..16)  -- 6 Loads + 10 MultiFluids
                MAX-ACCESS  read-only
                STATUS      current
                DESCRIPTION "Index of the Load to reach"
                ::= { energyEntry 6 }

engLoadRowStatus      OBJECT-TYPE
                SYNTAX       RowStatus
                MAX-ACCESS   read-create
                STATUS       current
                DESCRIPTION "The status of this conceptual row."
                ::= { energyEntry 10 }

engTotalHourMeter   OBJECT-TYPE
                SYNTAX      Unsigned32
                MAX-ACCESS  read-only
                STATUS      current
                DESCRIPTION "Total Hour meter for enegies (sec)"
                ::= { energyEntry 105000 }  
                
engTotalEnergyActivePos   OBJECT-TYPE
                SYNTAX      Unsigned32
                MAX-ACCESS  read-only
                STATUS      current
                DESCRIPTION "Total Positive Active Energy (kWh)"
                ::= { energyEntry 30000 }    
                
engTotalEnergyActiveResidualPos   OBJECT-TYPE
                SYNTAX      Unsigned32
                MAX-ACCESS  read-only
                STATUS      current
                DESCRIPTION "Total Residual Positive Active Energy (1/10 Wh)"
                ::= { energyEntry 30001 }    

engTotalEnergyActiveNeg   OBJECT-TYPE
                SYNTAX      Unsigned32
                MAX-ACCESS  read-only
                STATUS      current
                DESCRIPTION "Total Negative Active Energy (kWh)"
                ::= { energyEntry 30002 }    
                
engTotalEnergyActiveResidualNeg   OBJECT-TYPE
                SYNTAX      Unsigned32
                MAX-ACCESS  read-only
                STATUS      current
                DESCRIPTION "Total Residual Negative Active Energy (1/10 Wh)"
                ::= { energyEntry 30003 }    
                
engTotalEnergyReactivePos   OBJECT-TYPE
                SYNTAX      Unsigned32
                MAX-ACCESS  read-only
                STATUS      current
                DESCRIPTION "Total Positive Reactive Energy (kvarh)"
                ::= { energyEntry 30004 }    
                
engTotalEnergyReactiveResidualPos   OBJECT-TYPE
                SYNTAX      Unsigned32
                MAX-ACCESS  read-only
                STATUS      current
                DESCRIPTION "Total Residual Positive Reactive Energy (1/10 varh)"
                ::= { energyEntry 30005 }    

engTotalEnergyReactiveNeg   OBJECT-TYPE
                SYNTAX      Unsigned32
                MAX-ACCESS  read-only
                STATUS      current
                DESCRIPTION "Total Negative Reactive Energy (kvarh)"
                ::= { energyEntry 30006 }    
                
engTotalEnergyReactiveResidualNeg   OBJECT-TYPE
                SYNTAX      Unsigned32
                MAX-ACCESS  read-only
                STATUS      current
                DESCRIPTION "Total Residual Negative Reactive Energy (1/10 varh)"
                ::= { energyEntry 30007 }  
                
engTotalEnergyApparent   OBJECT-TYPE
                SYNTAX      Unsigned32
                MAX-ACCESS  read-only
                STATUS      current
                DESCRIPTION "Total Apparent Energy (kVAh)"
                ::= { energyEntry 30016 }    
                
engTotalEnergyApparentResidual   OBJECT-TYPE
                SYNTAX      Unsigned32
                MAX-ACCESS  read-only
                STATUS      current
                DESCRIPTION "Total Residual Apparent Energy (1/10 VAh)"
                ::= { energyEntry 30017 }    
	                
engTotalEnergyReactiveLaggingPos   OBJECT-TYPE
                SYNTAX      Unsigned32
                MAX-ACCESS  read-only
                STATUS      current
                DESCRIPTION "Total Reactive Lagging Positive Energy (kvarh)"
                ::= { energyEntry 30008 }    
                
engTotalEnergyReactiveLaggingResidualPos   OBJECT-TYPE
                SYNTAX      Unsigned32
                MAX-ACCESS  read-only
                STATUS      current
                DESCRIPTION "Total Residual Reactive Lagging Positive Energy (1/10 varh)"
                ::= { energyEntry 30009 }    			
		                
engTotalEnergyReactiveLaggingNeg   OBJECT-TYPE
                SYNTAX      Unsigned32
                MAX-ACCESS  read-only
                STATUS      current
                DESCRIPTION "Total Reactive Lagging Negative Energy (kvarh)"
                ::= { energyEntry 30010 }    
                
engTotalEnergyReactiveLaggingResidualNeg   OBJECT-TYPE
                SYNTAX      Unsigned32
                MAX-ACCESS  read-only
                STATUS      current
                DESCRIPTION "Total Residual Reactive Lagging Negative Energy (1/10 varh)"
                ::= { energyEntry 30011 } 			
	                
engTotalEnergyReactiveLeadingPos   OBJECT-TYPE
                SYNTAX      Unsigned32
                MAX-ACCESS  read-only
                STATUS      current
                DESCRIPTION "Total Reactive Leading Positive Energy (kvarh)"
                ::= { energyEntry 30012 }    
                
engTotalEnergyReactiveLeadingResidualPos   OBJECT-TYPE
                SYNTAX      Unsigned32
                MAX-ACCESS  read-only
                STATUS      current
                DESCRIPTION "Total Residual Reactive Leading Positive Energy (1/10 varh)"
                ::= { energyEntry 30013 }    			
		                
engTotalEnergyReactiveLeadingNeg   OBJECT-TYPE
                SYNTAX      Unsigned32
                MAX-ACCESS  read-only
                STATUS      current
                DESCRIPTION "Total Reactive Leading Negative Energy (kvarh)"
                ::= { energyEntry 30014 }    
                
engTotalEnergyReactiveLeadingResidualNeg   OBJECT-TYPE
                SYNTAX      Unsigned32
                MAX-ACCESS  read-only
                STATUS      current
                DESCRIPTION "Total Residual Reactive Leading Negative Energy (1/10 varh)"
                ::= { energyEntry 30015 }



engPartialHourMeter   OBJECT-TYPE
                SYNTAX      Unsigned32
                MAX-ACCESS  read-only
                STATUS      current
                DESCRIPTION "Partial Hour meter for enegies (sec)"
                ::= { energyEntry 105001 }  
                
engPartialEnergyActivePos   OBJECT-TYPE
                SYNTAX      Unsigned32
                MAX-ACCESS  read-only
                STATUS      current
                DESCRIPTION "Partial Positive Active Energy (kWh)"
                ::= { energyEntry 30018 }    
                
engPartialEnergyActiveResidualPos   OBJECT-TYPE
                SYNTAX      Unsigned32
                MAX-ACCESS  read-only
                STATUS      current
                DESCRIPTION "Partial Residual Positive Active Energy (1/10 Wh)"
                ::= { energyEntry 30019 }    

engPartialEnergyActiveNeg   OBJECT-TYPE
                SYNTAX      Unsigned32
                MAX-ACCESS  read-only
                STATUS      current
                DESCRIPTION "Partial Negative Active Energy (kWh)"
                ::= { energyEntry 30020 }    
                
engPartialEnergyActiveResidualNeg   OBJECT-TYPE
                SYNTAX      Unsigned32
                MAX-ACCESS  read-only
                STATUS      current
                DESCRIPTION "Partial Residual Negative Active Energy (1/10 Wh)"
                ::= { energyEntry 30021 }    
                
engPartialEnergyReactivePos   OBJECT-TYPE
                SYNTAX      Unsigned32
                MAX-ACCESS  read-only
                STATUS      current
                DESCRIPTION "Partial Positive Reactive Energy (kvarh)"
                ::= { energyEntry 30022 }    
                
engPartialEnergyReactiveResidualPos   OBJECT-TYPE
                SYNTAX      Unsigned32
                MAX-ACCESS  read-only
                STATUS      current
                DESCRIPTION "Partial Residual Positive Reactive Energy (1/10 varh)"
                ::= { energyEntry 30023 }    

engPartialEnergyReactiveNeg   OBJECT-TYPE
                SYNTAX      Unsigned32
                MAX-ACCESS  read-only
                STATUS      current
                DESCRIPTION "Partial Negative Reactive Energy (kvarh)"
                ::= { energyEntry 30024 }    
                
engPartialEnergyReactiveResidualNeg   OBJECT-TYPE
                SYNTAX      Unsigned32
                MAX-ACCESS  read-only
                STATUS      current
                DESCRIPTION "Partial Residual Negative Reactive Energy (1/10 varh)"
                ::= { energyEntry 30025 }  
                
engPartialEnergyApparent   OBJECT-TYPE
                SYNTAX      Unsigned32
                MAX-ACCESS  read-only
                STATUS      current
                DESCRIPTION "Partial Apparent Energy (kVAh)"
                ::= { energyEntry 30034 }    
                
engPartialEnergyApparentResidual   OBJECT-TYPE
                SYNTAX      Unsigned32
                MAX-ACCESS  read-only
                STATUS      current
                DESCRIPTION "Partial Residual Apparent Energy (1/10 VAh)"
                ::= { energyEntry 30035 }    


engLastPartialResetDate   OBJECT-TYPE
                SYNTAX      Unsigned32
                MAX-ACCESS  read-only
                STATUS      current
                DESCRIPTION "Last Partial Reset Date"
                ::= { energyEntry 30042 } 
				
--engLastPartialHourMeter   OBJECT-TYPE
--                SYNTAX      Unsigned32
--                MAX-ACCESS  read-only
--                STATUS      current
--                DESCRIPTION "Last Partial Hour meter for enegies (sec)"
--                ::= { energyEntry 65535 }  
                
engLastPartialEnergyActivePos   OBJECT-TYPE
                SYNTAX      Unsigned32
                MAX-ACCESS  read-only
                STATUS      current
                DESCRIPTION "Last Partial Positive Active Energy (kWh)"
                ::= { energyEntry 30043 }    
                
engLastPartialEnergyActiveResidualPos   OBJECT-TYPE
                SYNTAX      Unsigned32
                MAX-ACCESS  read-only
                STATUS      current
                DESCRIPTION "Last Partial Residual Positive Active Energy (1/10 Wh)"
                ::= { energyEntry 30076 }    

engLastPartialEnergyActiveNeg   OBJECT-TYPE
                SYNTAX      Unsigned32
                MAX-ACCESS  read-only
                STATUS      current
                DESCRIPTION "Last Partial Negative Active Energy (kWh)"
                ::= { energyEntry 30044 }    
                
engLastPartialEnergyActiveResidualNeg   OBJECT-TYPE
                SYNTAX      Unsigned32
                MAX-ACCESS  read-only
                STATUS      current
                DESCRIPTION "Last Partial Residual Negative Active Energy (1/10 Wh)"
                ::= { energyEntry 30077 }    
                
engLastPartialEnergyReactivePos   OBJECT-TYPE
                SYNTAX      Unsigned32
                MAX-ACCESS  read-only
                STATUS      current
                DESCRIPTION "Last Partial Positive Reactive Energy (kvarh)"
                ::= { energyEntry 30045 }    
                
engLastPartialEnergyReactiveResidualPos   OBJECT-TYPE
                SYNTAX      Unsigned32
                MAX-ACCESS  read-only
                STATUS      current
                DESCRIPTION "Last Partial Residual Positive Reactive Energy (1/10 varh)"
                ::= { energyEntry 30078 }    

engLastPartialEnergyReactiveNeg   OBJECT-TYPE
                SYNTAX      Unsigned32
                MAX-ACCESS  read-only
                STATUS      current
                DESCRIPTION "Last Partial Negative Reactive Energy (kvarh)"
                ::= { energyEntry 30046 }    
                
engLastPartialEnergyReactiveResidualNeg   OBJECT-TYPE
                SYNTAX      Unsigned32
                MAX-ACCESS  read-only
                STATUS      current
                DESCRIPTION "Last Partial Residual Negative Reactive Energy (1/10 varh)"
                ::= { energyEntry 30079 }  
                
engLastPartialEnergyApparent   OBJECT-TYPE
                SYNTAX      Unsigned32
                MAX-ACCESS  read-only
                STATUS      current
                DESCRIPTION "Last Partial Apparent Energy (kVAh)"
                ::= { energyEntry 30047 }    
                
engLastPartialEnergyApparentResidual   OBJECT-TYPE
                SYNTAX      Unsigned32
                MAX-ACCESS  read-only
                STATUS      current
                DESCRIPTION "Last Partial Residual Apparent Energy (1/10 VAh)"
                ::= { energyEntry 30080 } 



-- *******************************************************************************
-- ********************* MULTIFLUID TABLE ****************************************
multifluidTable       OBJECT-TYPE
                SYNTAX      SEQUENCE OF SeqMultifluidEnt
                MAX-ACCESS  not-accessible
                STATUS      current
                DESCRIPTION "Multifluids metrology Table"
                ::= { productMetrology 14 }

multifluidEntry       OBJECT-TYPE
                SYNTAX      SeqMultifluidEnt
                MAX-ACCESS  not-accessible
                STATUS      current
                DESCRIPTION "Multifluids Data Table for given Product Index and Load Index"
                INDEX  { mffModbusAddress, mffLoadIndex  }
                ::= { multifluidTable 1 }

mffModbusAddress    OBJECT-TYPE
                SYNTAX      Unsigned32(1..255)
                MAX-ACCESS  read-only
                STATUS      current
                DESCRIPTION "Modbus address of the product"
                ::= { multifluidEntry 1 }

mffProductIndex    OBJECT-TYPE
                SYNTAX      Unsigned32(1..33)  -- 32 Products + 1 Gateway
                MAX-ACCESS  read-only
                STATUS      current
                DESCRIPTION "Index of the Product to reach (1 = Gateway itself)"
                ::= { multifluidEntry 5 }

mffLoadIndex       OBJECT-TYPE
                SYNTAX      Unsigned32 (1..16)  -- 6 Loads + 10 MultiFluids
                MAX-ACCESS  read-only
                STATUS      current
                DESCRIPTION "Index of the Load to reach"
                ::= { multifluidEntry 6 }

mffLoadRowStatus      OBJECT-TYPE
                SYNTAX       RowStatus
                MAX-ACCESS   read-create
                STATUS       current
                DESCRIPTION "The status of this conceptual row."
                ::= { multifluidEntry 10 }

mffTotalMeter   OBJECT-TYPE
                SYNTAX      Integer32
                MAX-ACCESS  read-only
                STATUS      current
                DESCRIPTION "Total meter for multifluid (-)"
                ::= { multifluidEntry 65014 }  
                
mffPartialMeter OBJECT-TYPE
                SYNTAX      Integer32
                MAX-ACCESS  read-only
                STATUS      current
                DESCRIPTION "Partial meter for multifluid (-)"
                ::= { multifluidEntry 65015 }    
                
mffUnit         OBJECT-TYPE
                SYNTAX      DisplayString (SIZE (0..255))
                MAX-ACCESS  read-only
                STATUS      current
                DESCRIPTION "Unit of the multifluid meter"
                ::= { multifluidEntry 65012 }
                
mffWeight       OBJECT-TYPE
                SYNTAX      Integer32
                MAX-ACCESS  read-only
                STATUS      current
                DESCRIPTION "Weight of the pulses (1/100)"
                ::= { multifluidEntry 65013 }    
                
-- *******************************************************************************
-- ********************* INSTANTANEOUS TABLE *************************************
instantaneousTable       OBJECT-TYPE
                SYNTAX      SEQUENCE OF SeqInstantaneousEnt
                MAX-ACCESS  not-accessible
                STATUS      current
                DESCRIPTION "Instantaneous metrology Table"
                ::= { productMetrology 20 }

instantaneousEntry       OBJECT-TYPE
                SYNTAX      SeqInstantaneousEnt
                MAX-ACCESS  not-accessible
                STATUS      current
                DESCRIPTION "Instantaneous Data Table for given Product Index and Load Index"
                INDEX  { instModbusAddress, instLoadIndex  }
                ::= { instantaneousTable 1 }

instModbusAddress    OBJECT-TYPE
                SYNTAX      Unsigned32(1..255)
                MAX-ACCESS  read-only
                STATUS      current
                DESCRIPTION "Modbus address of the product"
                ::= { instantaneousEntry 1 }

instProductIndex    OBJECT-TYPE
                SYNTAX      Unsigned32(1..33)
                MAX-ACCESS  read-only
                STATUS      current
                DESCRIPTION "Index of the Product to reach (1 = Gateway itself)"
                ::= { instantaneousEntry 5 }

instLoadIndex       OBJECT-TYPE
                SYNTAX      Unsigned32(1..16)
                MAX-ACCESS  read-only
                STATUS      current
                DESCRIPTION "Index of the Load to reach"
                ::= { instantaneousEntry 6 }

instLoadRowStatus      OBJECT-TYPE
                SYNTAX       RowStatus
                MAX-ACCESS   read-create
                STATUS       current
                DESCRIPTION "The status of this conceptual row."
                ::= { instantaneousEntry 10 }

-- *******************
-- ** System *********
-- *******************
instVoltSystPhN   OBJECT-TYPE
                SYNTAX      Unsigned32
                MAX-ACCESS  read-only
                STATUS      current
                DESCRIPTION "System Ph-N Voltage (1/100 V)"
                ::= { instantaneousEntry 110004 } 
instVoltSystPhPh   OBJECT-TYPE
                SYNTAX      Unsigned32
                MAX-ACCESS  read-only
                STATUS      current
                DESCRIPTION "System Ph-Ph Voltage (1/100 V)"
                ::= { instantaneousEntry 110008 } 
instCurrentSyst   OBJECT-TYPE
                SYNTAX      Unsigned32
                MAX-ACCESS  read-only
                STATUS      current
                DESCRIPTION "System Current (mA)"
                ::= { instantaneousEntry 10004 } 
instFrequency   OBJECT-TYPE
                SYNTAX      Unsigned32
                MAX-ACCESS  read-only
                STATUS      current
                DESCRIPTION "System Frequency (mHz)"
                ::= { instantaneousEntry 40000 } 

-- *******************
-- ** Voltage ********
-- *******************
instVoltPhNV1   OBJECT-TYPE
                SYNTAX      Unsigned32
                MAX-ACCESS  read-only
                STATUS      current
                DESCRIPTION "Ph-N Voltage V1 (1/100 V)"
                ::= { instantaneousEntry 110000 } 
instVoltPhNV2   OBJECT-TYPE
                SYNTAX      Unsigned32
                MAX-ACCESS  read-only
                STATUS      current
                DESCRIPTION "Ph-N Voltage V2 (1/100 V)"
                ::= { instantaneousEntry 110001 } 
instVoltPhNV3   OBJECT-TYPE
                SYNTAX      Unsigned32
                MAX-ACCESS  read-only
                STATUS      current
                DESCRIPTION "Ph-N Voltage V3 (1/100 V)"
                ::= { instantaneousEntry 110002 } 
instVoltPhNVn   OBJECT-TYPE
                SYNTAX      Unsigned32
                MAX-ACCESS  read-only
                STATUS      current
                DESCRIPTION "Ph-N Voltage Vn (1/100 V)"
                ::= { instantaneousEntry 110003 } 
instVoltPhPhU12   OBJECT-TYPE
                SYNTAX      Unsigned32
                MAX-ACCESS  read-only
                STATUS      current
                DESCRIPTION "Ph-Ph Voltage U12 (1/100 V)"
                ::= { instantaneousEntry 110005 } 
instVoltPhPhU23   OBJECT-TYPE
                SYNTAX      Unsigned32
                MAX-ACCESS  read-only
                STATUS      current
                DESCRIPTION "Ph-Ph Voltage U23 (1/100 V)"
                ::= { instantaneousEntry 110006 } 
instVoltPhPhU31   OBJECT-TYPE
                SYNTAX      Unsigned32
                MAX-ACCESS  read-only
                STATUS      current
                DESCRIPTION "Ph-Ph Voltage U31 (1/100 V)"
                ::= { instantaneousEntry 110007 } 

-- *******************
-- ** Current ********
-- *******************
instCurrentI1   OBJECT-TYPE
                SYNTAX      Unsigned32
                MAX-ACCESS  read-only
                STATUS      current
                DESCRIPTION "Current I1 (mA)"
                ::= { instantaneousEntry 10000 }
instCurrentI2   OBJECT-TYPE
                SYNTAX      Unsigned32
                MAX-ACCESS  read-only
                STATUS      current
                DESCRIPTION "Current I2 (mA)"
                ::= { instantaneousEntry 10001 }
instCurrentI3   OBJECT-TYPE
                SYNTAX      Unsigned32
                MAX-ACCESS  read-only
                STATUS      current
                DESCRIPTION "Current I3 (mA)"
                ::= { instantaneousEntry 10002 }
instCurrentIn   OBJECT-TYPE
                SYNTAX      Unsigned32
                MAX-ACCESS  read-only
                STATUS      current
                DESCRIPTION "Current In (mA)"
                ::= { instantaneousEntry 10003 }
instCurrentInba   OBJECT-TYPE
                SYNTAX      Unsigned32
                MAX-ACCESS  read-only
                STATUS      current
                DESCRIPTION "Current Inba (1/100 %)"
                ::= { instantaneousEntry 10174 }
instCurrentIdir   OBJECT-TYPE
                SYNTAX      Unsigned32
                MAX-ACCESS  read-only
                STATUS      current
                DESCRIPTION "Current Idir (mA)"
                ::= { instantaneousEntry 10007 }
instCurrentIinv   OBJECT-TYPE
                SYNTAX      Unsigned32
                MAX-ACCESS  read-only
                STATUS      current
                DESCRIPTION "Current Iinv (mA)"
                ::= { instantaneousEntry 10008 }
instCurrentIhom   OBJECT-TYPE
                SYNTAX      Unsigned32
                MAX-ACCESS  read-only
                STATUS      current
                DESCRIPTION "Current Ihom (mA)"
                ::= { instantaneousEntry 10009 }
instCurrentInb   OBJECT-TYPE
                SYNTAX      Unsigned32
                MAX-ACCESS  read-only
                STATUS      current
                DESCRIPTION "Current Inb (1/100 %)"
                ::= { instantaneousEntry 10010 }
instCurrentIdn   OBJECT-TYPE
                SYNTAX      Unsigned32
                MAX-ACCESS  read-only
                STATUS      current
                DESCRIPTION "Current Idn A80 (mA)"
                ::= { instantaneousEntry 10005 }
instCurrentIpe   OBJECT-TYPE
                SYNTAX      Unsigned32
                MAX-ACCESS  read-only
                STATUS      current
                DESCRIPTION "Current Ipe A80 (mA)"
                ::= { instantaneousEntry 10006 }

-- *******************
-- ** Total Power ****
-- *******************
instPowerApparentNom   OBJECT-TYPE
                SYNTAX      Unsigned32
                MAX-ACCESS  read-only
                STATUS      current
                DESCRIPTION "Nominal Apparent Power (VA)"
                ::= { instantaneousEntry 85017 }
instTotalPowerActive   OBJECT-TYPE
                SYNTAX      Integer32
                MAX-ACCESS  read-only
                STATUS      current
                DESCRIPTION "Total Active Power (W)"
                ::= { instantaneousEntry 80003 }
instTotalPowerReactive   OBJECT-TYPE
                SYNTAX      Integer32
                MAX-ACCESS  read-only
                STATUS      current
                DESCRIPTION "Total Reactive Power (var)"
                ::= { instantaneousEntry 80007 }
instTotalPowerApparent   OBJECT-TYPE
                SYNTAX      Unsigned32
                MAX-ACCESS  read-only
                STATUS      current
                DESCRIPTION "Total Apparent Power (VA)"
                ::= { instantaneousEntry 80019 }
instTotalPowerFactor   OBJECT-TYPE
                SYNTAX      Integer32
                MAX-ACCESS  read-only
                STATUS      current
                DESCRIPTION "Total Power Factor (1/1000)"
                ::= { instantaneousEntry 75003 }
instTotalPowerFactorType   OBJECT-TYPE
                SYNTAX      Unsigned32
                MAX-ACCESS  read-only
                STATUS      current
                DESCRIPTION "Total Power Factor Type (1=Leading ; 2=Lagging)"
                ::= { instantaneousEntry 75007 }

-- *******************
-- ** Phasis Power ***
-- *******************
instPowerActiveP1   OBJECT-TYPE
                SYNTAX      Integer32
                MAX-ACCESS  read-only
                STATUS      current
                DESCRIPTION "P1 Active Power (W)"
                ::= { instantaneousEntry 80000 }       
instPowerActiveP2   OBJECT-TYPE
                SYNTAX      Integer32
                MAX-ACCESS  read-only
                STATUS      current
                DESCRIPTION "P2 Active Power (W)"
                ::= { instantaneousEntry 80001 } 
instPowerActiveP3   OBJECT-TYPE
                SYNTAX      Integer32
                MAX-ACCESS  read-only
                STATUS      current
                DESCRIPTION "P3 Active Power (W)"
                ::= { instantaneousEntry 80002 } 
instPowerReactiveQ1   OBJECT-TYPE
                SYNTAX      Integer32
                MAX-ACCESS  read-only
                STATUS      current
                DESCRIPTION "Q1 Reactive Power (var)"
                ::= { instantaneousEntry 80004 } 
instPowerReactiveQ2   OBJECT-TYPE
                SYNTAX      Integer32
                MAX-ACCESS  read-only
                STATUS      current
                DESCRIPTION "Q2 Reactive Power (var)"
                ::= { instantaneousEntry 80005 } 
instPowerReactiveQ3   OBJECT-TYPE
                SYNTAX      Integer32
                MAX-ACCESS  read-only
                STATUS      current
                DESCRIPTION "Q3 Reactive Power (var)"
                ::= { instantaneousEntry 80006 } 
instPowerApparentS1   OBJECT-TYPE
                SYNTAX      Unsigned32
                MAX-ACCESS  read-only
                STATUS      current
                DESCRIPTION "S1 Apparent Power (VA)"
                ::= { instantaneousEntry 80016 } 
instPowerApparentS2   OBJECT-TYPE
                SYNTAX      Unsigned32
                MAX-ACCESS  read-only
                STATUS      current
                DESCRIPTION "S2 Apparent Power (VA)"
                ::= { instantaneousEntry 80017 } 
instPowerApparentS3   OBJECT-TYPE
                SYNTAX      Unsigned32
                MAX-ACCESS  read-only
                STATUS      current
                DESCRIPTION "S3 Apparent Power (VA)"
                ::= { instantaneousEntry 80018 } 

-- *******************
-- ** Power Factor ***
-- *******************
instPowerFactorPF1   OBJECT-TYPE
                SYNTAX      Integer32
                MAX-ACCESS  read-only
                STATUS      current
                DESCRIPTION "PF1 Power Factor (1/1000)"
                ::= { instantaneousEntry 75000 }
instPowerFactorTypeSPF1   OBJECT-TYPE
                SYNTAX      Unsigned32
                MAX-ACCESS  read-only
                STATUS      current
                DESCRIPTION "sPF1 Power Factor Type (1=Leading ; 2=Lagging)"
                ::= { instantaneousEntry 75004 }
instPowerFactorPF2   OBJECT-TYPE
                SYNTAX      Integer32
                MAX-ACCESS  read-only
                STATUS      current
                DESCRIPTION "PF2 Power Factor (1/1000)"
                ::= { instantaneousEntry 75001 }
instPowerFactorTypeSPF2   OBJECT-TYPE
                SYNTAX      Unsigned32
                MAX-ACCESS  read-only
                STATUS      current
                DESCRIPTION "sPF1 Power Factor Type (1=Leading ; 2=Lagging)"
                ::= { instantaneousEntry 75005 }
instPowerFactorPF3   OBJECT-TYPE
                SYNTAX      Integer32
                MAX-ACCESS  read-only
                STATUS      current
                DESCRIPTION "PF3 Power Factor (1/1000)"
                ::= { instantaneousEntry 75002 }
instPowerFactorTypeSPF3   OBJECT-TYPE
                SYNTAX      Unsigned32
                MAX-ACCESS  read-only
                STATUS      current
                DESCRIPTION "sPF1 Power Factor Type (1=Leading ; 2=Lagging)"
                ::= { instantaneousEntry 75006 }

-- *******************************************************************************
-- ********************* AVERAGES TABLE ******************************************
averagesTable       OBJECT-TYPE
                SYNTAX      SEQUENCE OF SeqAveragesEnt
                MAX-ACCESS  not-accessible
                STATUS      current
                DESCRIPTION "Average metrology Table"
                ::= { productMetrology 30 }

averagesEntry       OBJECT-TYPE
                SYNTAX      SeqAveragesEnt
                MAX-ACCESS  not-accessible
                STATUS      current
                DESCRIPTION "Averages Data Table for given Product Index and Load Index"
                INDEX  { avgModbusAddress, avgLoadIndex  }
                ::= { averagesTable 1 }

avgModbusAddress    OBJECT-TYPE
                SYNTAX      Unsigned32(1..255)
                MAX-ACCESS  read-only
                STATUS      current
                DESCRIPTION "Modbus address of the product"
                ::= { averagesEntry 1 }

avgProductIndex    OBJECT-TYPE
                SYNTAX      Unsigned32(1..33)  -- 32 Products + 1 Gateway
                MAX-ACCESS  read-only
                STATUS      current
                DESCRIPTION "Index of the Product to reach (1 = Gateway itself)"
                ::= { averagesEntry 5 }

avgLoadIndex       OBJECT-TYPE
                SYNTAX      Unsigned32(1..16)  -- 6 Loads + 10 MultiFluids
                MAX-ACCESS  read-only
                STATUS      current
                DESCRIPTION "Index of the Load to reach"
                ::= { averagesEntry 6 }

avgLoadRowStatus      OBJECT-TYPE
                SYNTAX       RowStatus
                MAX-ACCESS   read-create
                STATUS       current
                DESCRIPTION "The status of this conceptual row."
                ::= { averagesEntry 10 }

avgDateLastInstance   OBJECT-TYPE
                SYNTAX      Unsigned32
                MAX-ACCESS  read-only
                STATUS      current
                DESCRIPTION "Date of last instance (measured point)"
                ::= { averagesEntry 45004 } 

-- *******************
-- ** System *********
-- *******************
avgVoltSystPhN   OBJECT-TYPE
                SYNTAX      Unsigned32
                MAX-ACCESS  read-only
                STATUS      current
                DESCRIPTION "System Ph-N Voltage (1/100 V)"
                ::= { averagesEntry 110034 } 
avgVoltSystPhPh   OBJECT-TYPE
                SYNTAX      Unsigned32
                MAX-ACCESS  read-only
                STATUS      current
                DESCRIPTION "System Ph-Ph Voltage (1/100 V)"
                ::= { averagesEntry 110038 } 
avgCurrentSyst   OBJECT-TYPE
                SYNTAX      Unsigned32
                MAX-ACCESS  read-only
                STATUS      current
                DESCRIPTION "System Current (W)"
                ::= { averagesEntry 10027 } 
avgFrequency   OBJECT-TYPE
                SYNTAX      Unsigned32
                MAX-ACCESS  read-only
                STATUS      current
                DESCRIPTION "System Frequency (mHz)"
                ::= { averagesEntry 40001 } 

-- *******************
-- ** Voltage ********
-- *******************
avgVoltPhNV1   OBJECT-TYPE
                SYNTAX      Unsigned32
                MAX-ACCESS  read-only
                STATUS      current
                DESCRIPTION "Ph-N Voltage V1 (1/100 V)"
                ::= { averagesEntry 110030 } 
avgVoltPhNV2   OBJECT-TYPE
                SYNTAX      Unsigned32
                MAX-ACCESS  read-only
                STATUS      current
                DESCRIPTION "Ph-N Voltage V2 (1/100 V)"
                ::= { averagesEntry 110031 } 
avgVoltPhNV3   OBJECT-TYPE
                SYNTAX      Unsigned32
                MAX-ACCESS  read-only
                STATUS      current
                DESCRIPTION "Ph-N Voltage V3 (1/100 V)"
                ::= { averagesEntry 110032 } 
avgVoltPhNVn   OBJECT-TYPE
                SYNTAX      Unsigned32
                MAX-ACCESS  read-only
                STATUS      current
                DESCRIPTION "Ph-N Voltage Vn (1/100 V)"
                ::= { averagesEntry 110033 }
avgVoltPhPhU12   OBJECT-TYPE
                SYNTAX      Unsigned32
                MAX-ACCESS  read-only
                STATUS      current
                DESCRIPTION "Ph-Ph Voltage U12 (1/100 V)"
                ::= { averagesEntry 110035 }  
avgVoltPhPhU23   OBJECT-TYPE
                SYNTAX      Unsigned32
                MAX-ACCESS  read-only
                STATUS      current
                DESCRIPTION "Ph-Ph Voltage U23 (1/100 V)"
                ::= { averagesEntry 110036 }  
avgVoltPhPhU31   OBJECT-TYPE
                SYNTAX      Unsigned32
                MAX-ACCESS  read-only
                STATUS      current
                DESCRIPTION "Ph-Ph Voltage U31 (1/100 V)"
                ::= { averagesEntry 110037 }  

-- *******************
-- ** Current ********
-- *******************
avgCurrentI1   OBJECT-TYPE
                SYNTAX      Unsigned32
                MAX-ACCESS  read-only
                STATUS      current
                DESCRIPTION "Current I1 (mA)"
                ::= { averagesEntry 10023 }
avgCurrentI2   OBJECT-TYPE
                SYNTAX      Unsigned32
                MAX-ACCESS  read-only
                STATUS      current
                DESCRIPTION "Current I2 (mA)"
                ::= { averagesEntry 10024 }
avgCurrentI3   OBJECT-TYPE
                SYNTAX      Unsigned32
                MAX-ACCESS  read-only
                STATUS      current
                DESCRIPTION "Current I3 (mA)"
                ::= { averagesEntry 10025 }
avgCurrentIn   OBJECT-TYPE
                SYNTAX      Unsigned32
                MAX-ACCESS  read-only
                STATUS      current
                DESCRIPTION "Current In (mA)"
                ::= { averagesEntry 10026 }
avgCurrentInba   OBJECT-TYPE
                SYNTAX      Unsigned32
                MAX-ACCESS  read-only
                STATUS      current
                DESCRIPTION "Current Inba (1/100 %)"
                ::= { averagesEntry 10175 }
avgCurrentIdir   OBJECT-TYPE
                SYNTAX      Unsigned32
                MAX-ACCESS  read-only
                STATUS      current
                DESCRIPTION "Current Idir (mA)"
                ::= { averagesEntry 10030 }
avgCurrentIinv   OBJECT-TYPE
                SYNTAX      Unsigned32
                MAX-ACCESS  read-only
                STATUS      current
                DESCRIPTION "Current Iinv (mA)"
                ::= { averagesEntry 10031 }
avgCurrentIhom   OBJECT-TYPE
                SYNTAX      Unsigned32
                MAX-ACCESS  read-only
                STATUS      current
                DESCRIPTION "Current Ihom (mA)"
                ::= { averagesEntry 10032 }
avgCurrentInb   OBJECT-TYPE
                SYNTAX      Unsigned32
                MAX-ACCESS  read-only
                STATUS      current
                DESCRIPTION "Current Inb (1/100 %)"
                ::= { averagesEntry 10033 }

-- *******************
-- ** Total Power ****
-- *******************
avgTotalPowerActive   OBJECT-TYPE
                SYNTAX      Integer32
                MAX-ACCESS  read-only
                STATUS      current
                DESCRIPTION "Total Active Power (W)"
                ::= { averagesEntry 80031 }
avgTotalPowerReactive   OBJECT-TYPE
                SYNTAX      Integer32
                MAX-ACCESS  read-only
                STATUS      current
                DESCRIPTION "Total Reactive Power (var)"
                ::= { averagesEntry 80035 }
avgTotalPowerApparent   OBJECT-TYPE
                SYNTAX      Unsigned32
                MAX-ACCESS  read-only
                STATUS      current
                DESCRIPTION "Total Apparent Power (VA)"
                ::= { averagesEntry 80047 }
avgTotalPowerFactor   OBJECT-TYPE
                SYNTAX      Integer32
                MAX-ACCESS  read-only
                STATUS      current
                DESCRIPTION "Total Power Factor (1/1000)"
                ::= { averagesEntry 75011 }
avgTotalPowerFactorType   OBJECT-TYPE
                SYNTAX      Unsigned32
                MAX-ACCESS  read-only
                STATUS      current
                DESCRIPTION "Total Power Factor Type (1=Leading ; 2=Lagging)"
                ::= { averagesEntry 75015 }

-- *******************
-- ** Phasis Power ***
-- *******************
avgPowerActiveP1   OBJECT-TYPE
                SYNTAX      Integer32
                MAX-ACCESS  read-only
                STATUS      current
                DESCRIPTION "P1 Active Power (W)"
                ::= { averagesEntry 80028 }
avgPowerActiveP2   OBJECT-TYPE
                SYNTAX      Integer32
                MAX-ACCESS  read-only
                STATUS      current
                DESCRIPTION "P2 Active Power (W)"
                ::= { averagesEntry 80029 }
avgPowerActiveP3   OBJECT-TYPE
                SYNTAX      Integer32
                MAX-ACCESS  read-only
                STATUS      current
                DESCRIPTION "P3 Active Power (W)"
                ::= { averagesEntry 80030 }
avgPowerReactiveQ1   OBJECT-TYPE
                SYNTAX      Integer32
                MAX-ACCESS  read-only
                STATUS      current
                DESCRIPTION "Q1 Reactive Power (var)"
                ::= { averagesEntry 80032 } 
avgPowerReactiveQ2   OBJECT-TYPE
                SYNTAX      Integer32
                MAX-ACCESS  read-only
                STATUS      current
                DESCRIPTION "Q2 Reactive Power (var)"
                ::= { averagesEntry 80033 } 
avgPowerReactiveQ3   OBJECT-TYPE
                SYNTAX      Integer32
                MAX-ACCESS  read-only
                STATUS      current
                DESCRIPTION "Q3 Reactive Power (var)"
                ::= { averagesEntry 80034 } 
avgPowerApparentS1   OBJECT-TYPE
                SYNTAX      Unsigned32
                MAX-ACCESS  read-only
                STATUS      current
                DESCRIPTION "S1 Apparent Power (VA)"
                ::= { averagesEntry 80044 }  
avgPowerApparentS2   OBJECT-TYPE
                SYNTAX      Unsigned32
                MAX-ACCESS  read-only
                STATUS      current
                DESCRIPTION "S2 Apparent Power (VA)"
                ::= { averagesEntry 80045 }  
avgPowerApparentS3   OBJECT-TYPE
                SYNTAX      Unsigned32
                MAX-ACCESS  read-only
                STATUS      current
                DESCRIPTION "S3 Apparent Power (VA)"
                ::= { averagesEntry 80046 }  

-- *******************
-- ** Power Factor ***
-- *******************
avgPowerFactorPF1   OBJECT-TYPE
                SYNTAX      Integer32
                MAX-ACCESS  read-only
                STATUS      current
                DESCRIPTION "PF1 Power Factor (1/1000)"
                ::= { averagesEntry 75008 }
avgPowerFactorTypeSPF1   OBJECT-TYPE
                SYNTAX      Unsigned32
                MAX-ACCESS  read-only
                STATUS      current
                DESCRIPTION "sPF1 Power Factor Type (1=Leading ; 2=Lagging)"
                ::= { averagesEntry 75012 }
avgPowerFactorPF2   OBJECT-TYPE
                SYNTAX      Integer32
                MAX-ACCESS  read-only
                STATUS      current
                DESCRIPTION "PF2 Power Factor (1/1000)"
                ::= { averagesEntry 75009 }
avgPowerFactorTypeSPF2   OBJECT-TYPE
                SYNTAX      Unsigned32
                MAX-ACCESS  read-only
                STATUS      current
                DESCRIPTION "sPF1 Power Factor Type (1=Leading ; 2=Lagging)"
                ::= { averagesEntry 75013 }
avgPowerFactorPF3   OBJECT-TYPE
                SYNTAX      Integer32
                MAX-ACCESS  read-only
                STATUS      current
                DESCRIPTION "PF3 Power Factor (1/1000)"
                ::= { averagesEntry 75010 }
avgPowerFactorTypeSPF3   OBJECT-TYPE
                SYNTAX      Unsigned32
                MAX-ACCESS  read-only
                STATUS      current
                DESCRIPTION "sPF1 Power Factor Type (1=Leading ; 2=Lagging)"
                ::= { averagesEntry 75014 }

-- *******************************************************************************
-- ********************* MEASUREMENT MaxInstantaneous TABLE *************************
maxInstantaneousTable       OBJECT-TYPE
                SYNTAX      SEQUENCE OF SeqMaxInstantaneousEnt
                MAX-ACCESS  not-accessible
                STATUS      current
                DESCRIPTION "Max Instantaneous metrology Table"
                ::= { productMetrology 40 }

maxInstantaneousEntry       OBJECT-TYPE
                SYNTAX      SeqMaxInstantaneousEnt
                MAX-ACCESS  not-accessible
                STATUS      current
                DESCRIPTION "Max Instantaneous Data Table for given Product Index and Load Index"
                INDEX  { maxInstModbusAddress, maxInstLoadIndex  }
                ::= { maxInstantaneousTable 1 }

maxInstModbusAddress    OBJECT-TYPE
                SYNTAX      Unsigned32(1..255)
                MAX-ACCESS  read-only
                STATUS      current
                DESCRIPTION "Modbus address of the product"
                ::= { maxInstantaneousEntry 1 }

maxInstProductIndex    OBJECT-TYPE
                SYNTAX      Unsigned32(1..33)  -- 32 Products + 1 Gateway
                MAX-ACCESS  read-only
                STATUS      current
                DESCRIPTION "Index of the Product to reach (1 = Gateway itself)"
                ::= { maxInstantaneousEntry 5 }

maxInstLoadIndex       OBJECT-TYPE
                SYNTAX      Unsigned32(1..16)  -- 6 Loads + 10 MultiFluids
                MAX-ACCESS  read-only
                STATUS      current
                DESCRIPTION "Index of the Load to reach"
                ::= { maxInstantaneousEntry 6 }

maxInstLoadRowStatus      OBJECT-TYPE
                SYNTAX       RowStatus
                MAX-ACCESS   read-create
                STATUS       current
                DESCRIPTION "The status of this conceptual row."
                ::= { maxInstantaneousEntry 10 }

-- *******************
-- ** System *********
-- *******************
maxInstFrequency   OBJECT-TYPE
                SYNTAX      Unsigned32
                MAX-ACCESS  read-only
                STATUS      current
                DESCRIPTION "System Frequency (mHz)"
                ::= { maxInstantaneousEntry 40006 }
maxInstFrequencyDate   OBJECT-TYPE
                SYNTAX      Unsigned32
                MAX-ACCESS  read-only
                STATUS      current
                DESCRIPTION "System Frequency Date"
                ::= { maxInstantaneousEntry 40007 }
                
-- *******************
-- ** Voltage ********
-- *******************
maxInstVoltPhNV1   OBJECT-TYPE
                SYNTAX      Unsigned32
                MAX-ACCESS  read-only
                STATUS      current
                DESCRIPTION "Ph-N Voltage V1 (1/100 V)"
                ::= { maxInstantaneousEntry 110098 } 
maxInstVoltPhNV1Date   OBJECT-TYPE
                SYNTAX      Unsigned32
                MAX-ACCESS  read-only
                STATUS      current
                DESCRIPTION "Ph-N Voltage V1 Date"
                ::= { maxInstantaneousEntry 110099 }
maxInstVoltPhNV2   OBJECT-TYPE
                SYNTAX      Unsigned32
                MAX-ACCESS  read-only
                STATUS      current
                DESCRIPTION "Ph-N Voltage V2 (1/100 V)"
                ::= { maxInstantaneousEntry 110100 } 
maxInstVoltPhNV2Date   OBJECT-TYPE
                SYNTAX      Unsigned32
                MAX-ACCESS  read-only
                STATUS      current
                DESCRIPTION "Ph-N Voltage V2 Date"
                ::= { maxInstantaneousEntry 110101 }
maxInstVoltPhNV3   OBJECT-TYPE
                SYNTAX      Unsigned32
                MAX-ACCESS  read-only
                STATUS      current
                DESCRIPTION "Ph-N Voltage V3 (1/100 V)"
                ::= { maxInstantaneousEntry 110102 } 
maxInstVoltPhNV3Date   OBJECT-TYPE
                SYNTAX      Unsigned32
                MAX-ACCESS  read-only
                STATUS      current
                DESCRIPTION "Ph-N Voltage V3Date"
                ::= { maxInstantaneousEntry 110103 }
maxInstVoltPhNVn   OBJECT-TYPE
                SYNTAX      Unsigned32
                MAX-ACCESS  read-only
                STATUS      current
                DESCRIPTION "Ph-N Voltage Vn (1/100 V)"
                ::= { maxInstantaneousEntry 110104 }
maxInstVoltPhNVnDate   OBJECT-TYPE
                SYNTAX      Unsigned32
                MAX-ACCESS  read-only
                STATUS      current
                DESCRIPTION "Ph-N Voltage Vn Date"
                ::= { maxInstantaneousEntry 110105 }  
maxInstVoltPhPhU12   OBJECT-TYPE
                SYNTAX      Unsigned32
                MAX-ACCESS  read-only
                STATUS      current
                DESCRIPTION "Ph-Ph Voltage U12 (1/100 V)"
                ::= { maxInstantaneousEntry 110108 }  
maxInstVoltPhPhU12Date   OBJECT-TYPE
                SYNTAX      Unsigned32
                MAX-ACCESS  read-only
                STATUS      current
                DESCRIPTION "Ph-Ph Voltage U12 Date"
                ::= { maxInstantaneousEntry 110109 } 
maxInstVoltPhPhU23   OBJECT-TYPE
                SYNTAX      Unsigned32
                MAX-ACCESS  read-only
                STATUS      current
                DESCRIPTION "Ph-Ph Voltage U23 (1/100 V)"
                ::= { maxInstantaneousEntry 110110 }  
maxInstVoltPhPhU23Date   OBJECT-TYPE
                SYNTAX      Unsigned32
                MAX-ACCESS  read-only
                STATUS      current
                DESCRIPTION "Ph-Ph Voltage U23 Date"
                ::= { maxInstantaneousEntry 110111 } 
maxInstVoltPhPhU31   OBJECT-TYPE
                SYNTAX      Unsigned32
                MAX-ACCESS  read-only
                STATUS      current
                DESCRIPTION "Ph-Ph Voltage U31 (1/100 V)"
                ::= { maxInstantaneousEntry 110112 }  
maxInstVoltPhPhU31Date   OBJECT-TYPE
                SYNTAX      Unsigned32
                MAX-ACCESS  read-only
                STATUS      current
                DESCRIPTION "Ph-Ph Voltage U31 Date"
                ::= { maxInstantaneousEntry 110113 } 

-- *******************
-- ** Current ********
-- *******************
maxInstCurrentI1   OBJECT-TYPE
                SYNTAX      Unsigned32
                MAX-ACCESS  read-only
                STATUS      current
                DESCRIPTION "Current I1 (mA)"
                ::= { maxInstantaneousEntry 10074 }
maxInstCurrentI1Date   OBJECT-TYPE
                SYNTAX      Unsigned32
                MAX-ACCESS  read-only
                STATUS      current
                DESCRIPTION "Current I1 Date"
                ::= { maxInstantaneousEntry 10075 }
maxInstCurrentI2   OBJECT-TYPE
                SYNTAX      Unsigned32
                MAX-ACCESS  read-only
                STATUS      current
                DESCRIPTION "Current I2 (mA)"
                ::= { maxInstantaneousEntry 10076 }
maxInstCurrentI2Date   OBJECT-TYPE
                SYNTAX      Unsigned32
                MAX-ACCESS  read-only
                STATUS      current
                DESCRIPTION "Current I2 Date"
                ::= { maxInstantaneousEntry 10077 }
maxInstCurrentI3   OBJECT-TYPE
                SYNTAX      Unsigned32
                MAX-ACCESS  read-only
                STATUS      current
                DESCRIPTION "Current I3 (mA)"
                ::= { maxInstantaneousEntry 10078 }
maxInstCurrentI3Date   OBJECT-TYPE
                SYNTAX      Unsigned32
                MAX-ACCESS  read-only
                STATUS      current
                DESCRIPTION "Current I3 Date"
                ::= { maxInstantaneousEntry 10079 }    
maxInstCurrentIn   OBJECT-TYPE
                SYNTAX      Unsigned32
                MAX-ACCESS  read-only
                STATUS      current
                DESCRIPTION "Current In (mA)"
                ::= { maxInstantaneousEntry 10080 }
maxInstCurrentInDate   OBJECT-TYPE
                SYNTAX      Unsigned32
                MAX-ACCESS  read-only
                STATUS      current
                DESCRIPTION "Current In Date"
                ::= { maxInstantaneousEntry 10081 }

-- *******************
-- ** Total Power ****
-- *******************
maxInstTotalPowerActive   OBJECT-TYPE
                SYNTAX      Integer32
                MAX-ACCESS  read-only
                STATUS      current
                DESCRIPTION "Total Active Power (W)"
                ::= { maxInstantaneousEntry 80102 }
maxInstTotalPowerActiveDate   OBJECT-TYPE
                SYNTAX      Unsigned32
                MAX-ACCESS  read-only
                STATUS      current
                DESCRIPTION "Total Active Power Date"
                ::= { maxInstantaneousEntry 80103 }
maxInstTotalPowerReactive   OBJECT-TYPE
                SYNTAX      Integer32
                MAX-ACCESS  read-only
                STATUS      current
                DESCRIPTION "Total Reactive Power (var)"
                ::= { maxInstantaneousEntry 80110 }
maxInstTotalPowerReactiveDate   OBJECT-TYPE
                SYNTAX      Unsigned32
                MAX-ACCESS  read-only
                STATUS      current
                DESCRIPTION "Total Reactive Power Date"
                ::= { maxInstantaneousEntry 80111 }
maxInstTotalPowerApparent   OBJECT-TYPE
                SYNTAX      Unsigned32
                MAX-ACCESS  read-only
                STATUS      current
                DESCRIPTION "Total Apparent Power (VA)"
                ::= { maxInstantaneousEntry 80126 }
maxInstTotalPowerApparentDate   OBJECT-TYPE
                SYNTAX      Unsigned32
                MAX-ACCESS  read-only
                STATUS      current
                DESCRIPTION "Total Apparent Power Date"
                ::= { maxInstantaneousEntry 80127 }
maxInstTotalPowerFactor   OBJECT-TYPE
                SYNTAX      Integer32
                MAX-ACCESS  read-only
                STATUS      current
                DESCRIPTION "Total Power Factor (1/1000)"
                ::= { maxInstantaneousEntry 75034 }
maxInstTotalPowerFactorType   OBJECT-TYPE
                SYNTAX      Unsigned32
                MAX-ACCESS  read-only
                STATUS      current
                DESCRIPTION "Total Power Factor Type (1=Leading ; 2=Lagging)"
                ::= { maxInstantaneousEntry 75039 }
maxInstTotalPowerFactorDate   OBJECT-TYPE
                SYNTAX      Unsigned32
                MAX-ACCESS  read-only
                STATUS      current
                DESCRIPTION "Total Power Factor Date"
                ::= { maxInstantaneousEntry 75035 }

-- *******************
-- ** Phasis Power ***
-- *******************
maxInstPowerActiveP1   OBJECT-TYPE
                SYNTAX      Integer32
                MAX-ACCESS  read-only
                STATUS      current
                DESCRIPTION "P1 Active Power (W)"
                ::= { maxInstantaneousEntry 80096 }
maxInstPowerActiveP1Date   OBJECT-TYPE
                SYNTAX      Unsigned32
                MAX-ACCESS  read-only
                STATUS      current
                DESCRIPTION "P1 Active Power Date"
                ::= { maxInstantaneousEntry 80097 }
maxInstPowerActiveP2   OBJECT-TYPE
                SYNTAX      Integer32
                MAX-ACCESS  read-only
                STATUS      current
                DESCRIPTION "P2 Active Power (W)"
                ::= { maxInstantaneousEntry 80098 }
maxInstPowerActiveP2Date   OBJECT-TYPE
                SYNTAX      Unsigned32
                MAX-ACCESS  read-only
                STATUS      current
                DESCRIPTION "P2 Active Power Date"
                ::= { maxInstantaneousEntry 80099 } 
maxInstPowerActiveP3   OBJECT-TYPE
                SYNTAX      Integer32
                MAX-ACCESS  read-only
                STATUS      current
                DESCRIPTION "P3 Active Power (W)"
                ::= { maxInstantaneousEntry 80100 }
maxInstPowerActiveP3Date   OBJECT-TYPE
                SYNTAX      Unsigned32
                MAX-ACCESS  read-only
                STATUS      current
                DESCRIPTION "P3 Active Power Date"
                ::= { maxInstantaneousEntry 80101 } 
maxInstPowerReactiveQ1   OBJECT-TYPE
                SYNTAX      Integer32
                MAX-ACCESS  read-only
                STATUS      current
                DESCRIPTION "Q1 Reactive Power (var)"
                ::= { maxInstantaneousEntry 80104 } 
maxInstPowerReactiveQ1Date   OBJECT-TYPE
                SYNTAX      Unsigned32
                MAX-ACCESS  read-only
                STATUS      current
                DESCRIPTION "Q1 Reactive Power Date"
                ::= { maxInstantaneousEntry 80105 } 
maxInstPowerReactiveQ2   OBJECT-TYPE
                SYNTAX      Integer32
                MAX-ACCESS  read-only
                STATUS      current
                DESCRIPTION "Q2 Reactive Power (var)"
                ::= { maxInstantaneousEntry 80106 } 
maxInstPowerReactiveQ2Date   OBJECT-TYPE
                SYNTAX      Unsigned32
                MAX-ACCESS  read-only
                STATUS      current
                DESCRIPTION "Q2 Reactive Power Date"
                ::= { maxInstantaneousEntry 80107 }  
maxInstPowerReactiveQ3   OBJECT-TYPE
                SYNTAX      Integer32
                MAX-ACCESS  read-only
                STATUS      current
                DESCRIPTION "Q3 Reactive Power (var)"
                ::= { maxInstantaneousEntry 80108 } 
maxInstPowerReactiveQ3Date   OBJECT-TYPE
                SYNTAX      Unsigned32
                MAX-ACCESS  read-only
                STATUS      current
                DESCRIPTION "Q3 Reactive Power Date"
                ::= { maxInstantaneousEntry 80109 }  
maxInstPowerApparentS1   OBJECT-TYPE
                SYNTAX      Unsigned32
                MAX-ACCESS  read-only
                STATUS      current
                DESCRIPTION "S1 Apparent Power (VA)"
                ::= { maxInstantaneousEntry 80120 }  
maxInstPowerApparentS1Date   OBJECT-TYPE
                SYNTAX      Unsigned32
                MAX-ACCESS  read-only
                STATUS      current
                DESCRIPTION "S1 Apparent Power Date"
                ::= { maxInstantaneousEntry 80121 } 
maxInstPowerApparentS2   OBJECT-TYPE
                SYNTAX      Unsigned32
                MAX-ACCESS  read-only
                STATUS      current
                DESCRIPTION "S2 Apparent Power (VA)"
                ::= { maxInstantaneousEntry 80122 }  
maxInstPowerApparentS2Date   OBJECT-TYPE
                SYNTAX      Unsigned32
                MAX-ACCESS  read-only
                STATUS      current
                DESCRIPTION "S2 Apparent Power Date"
                ::= { maxInstantaneousEntry 80123 } 
maxInstPowerApparentS3   OBJECT-TYPE
                SYNTAX      Unsigned32
                MAX-ACCESS  read-only
                STATUS      current
                DESCRIPTION "S3 Apparent Power (VA)"
                ::= { maxInstantaneousEntry 80124 }  
maxInstPowerApparentS3Date   OBJECT-TYPE
                SYNTAX      Unsigned32
                MAX-ACCESS  read-only
                STATUS      current
                DESCRIPTION "S3 Apparent Power Date"
                ::= { maxInstantaneousEntry 80125 } 

-- *******************
-- ** Power Factor ***
-- *******************
maxInstPowerFactorPF1   OBJECT-TYPE
                SYNTAX      Integer32
                MAX-ACCESS  read-only
                STATUS      current
                DESCRIPTION "PF1 Power Factor (1/1000)"
                ::= { maxInstantaneousEntry 75028 }
maxInstPowerFactorTypeSPF1   OBJECT-TYPE
                SYNTAX      Unsigned32
                MAX-ACCESS  read-only
                STATUS      current
                DESCRIPTION "sPF1 Power Factor Type (1=Leading ; 2=Lagging)"
                ::= { maxInstantaneousEntry 75036 }
maxInstPowerFactorPF1Date   OBJECT-TYPE
                SYNTAX      Unsigned32
                MAX-ACCESS  read-only
                STATUS      current
                DESCRIPTION "PF1 Power Factor Date"
                ::= { maxInstantaneousEntry 75029 }
maxInstPowerFactorPF2   OBJECT-TYPE
                SYNTAX      Integer32
                MAX-ACCESS  read-only
                STATUS      current
                DESCRIPTION "PF2 Power Factor (1/1000)"
                ::= { maxInstantaneousEntry 75030 }
maxInstPowerFactorTypeSPF2   OBJECT-TYPE
                SYNTAX      Unsigned32
                MAX-ACCESS  read-only
                STATUS      current
                DESCRIPTION "sPF1 Power Factor Type (1=Leading ; 2=Lagging)"
                ::= { maxInstantaneousEntry 75037 }
maxInstPowerFactorPF2Date   OBJECT-TYPE
                SYNTAX      Unsigned32
                MAX-ACCESS  read-only
                STATUS      current
                DESCRIPTION "PF2 Power Factor Date"
                ::= { maxInstantaneousEntry 75031 }
maxInstPowerFactorPF3   OBJECT-TYPE
                SYNTAX      Integer32
                MAX-ACCESS  read-only
                STATUS      current
                DESCRIPTION "PF3 Power Factor (1/1000)"
                ::= { maxInstantaneousEntry 75032 }
maxInstPowerFactorTypeSPF3   OBJECT-TYPE
                SYNTAX      Unsigned32
                MAX-ACCESS  read-only
                STATUS      current
                DESCRIPTION "sPF1 Power Factor Type (1=Leading ; 2=Lagging)"
                ::= { maxInstantaneousEntry 75038 }
maxInstPowerFactorPF3Date   OBJECT-TYPE
                SYNTAX      Unsigned32
                MAX-ACCESS  read-only
                STATUS      current
                DESCRIPTION "PF3 Power Factor Date"
                ::= { maxInstantaneousEntry 75033 }

-- *******************************************************************************
-- ********************* MEASUREMENT MinInstantaneous TABLE *************************
minInstantaneousTable       OBJECT-TYPE
                SYNTAX      SEQUENCE OF SeqMinInstantaneousEnt
                MAX-ACCESS  not-accessible
                STATUS      current
                DESCRIPTION "Min Instantaneous Metrology Table"
                ::= { productMetrology 50 }

minInstantaneousEntry       OBJECT-TYPE
                SYNTAX      SeqMinInstantaneousEnt
                MAX-ACCESS  not-accessible
                STATUS      current
                DESCRIPTION "Min Instantaneous Data Table for given Product Index and Load Index"
                INDEX  { minInstModbusAddress, minInstLoadIndex  }
                ::= { minInstantaneousTable 1 }

minInstModbusAddress    OBJECT-TYPE
                SYNTAX      Unsigned32(1..255)
                MAX-ACCESS  read-only
                STATUS      current
                DESCRIPTION "Modbus address of the product"
                ::= { minInstantaneousEntry 1 }
                
minInstProductIndex    OBJECT-TYPE
                SYNTAX      Unsigned32(1..33)  -- 32 Products + 1 Gateway
                MAX-ACCESS  read-only
                STATUS      current
                DESCRIPTION "Index of the Product to reach (1 = Gateway itself)"
                ::= { minInstantaneousEntry 5 }

minInstLoadIndex       OBJECT-TYPE
                SYNTAX      Unsigned32(1..16)  -- 6 Loads + 10 MultiFluids
                MAX-ACCESS  read-only
                STATUS      current
                DESCRIPTION "Index of the Load to reach"
                ::= { minInstantaneousEntry 6 }

minInstLoadRowStatus      OBJECT-TYPE
                SYNTAX       RowStatus
                MAX-ACCESS   read-create
                STATUS       current
                DESCRIPTION "The status of this conceptual row."
                ::= { minInstantaneousEntry 10 }

-- *******************
-- ** System *********
-- *******************
minInstFrequency   OBJECT-TYPE
                SYNTAX      Unsigned32
                MAX-ACCESS  read-only
                STATUS      current
                DESCRIPTION "System Frequency (1/1000 Hz)"
                ::= { minInstantaneousEntry 40008 }
minInstFrequencyDate   OBJECT-TYPE
                SYNTAX      Unsigned32
                MAX-ACCESS  read-only
                STATUS      current
                DESCRIPTION "System Frequency Date"
                ::= { minInstantaneousEntry 40009 }
                
-- *******************
-- ** Voltage ********
-- *******************
minInstVoltPhNV1   OBJECT-TYPE
                SYNTAX      Unsigned32
                MAX-ACCESS  read-only
                STATUS      current
                DESCRIPTION "Ph-N Voltage V1 (1/100 V)"
                ::= { minInstantaneousEntry 110060 } 
minInstVoltPhNV1Date   OBJECT-TYPE
                SYNTAX      Unsigned32
                MAX-ACCESS  read-only
                STATUS      current
                DESCRIPTION "Ph-N Voltage V1 Date"
                ::= { minInstantaneousEntry 110061 }
minInstVoltPhNV2   OBJECT-TYPE
                SYNTAX      Unsigned32
                MAX-ACCESS  read-only
                STATUS      current
                DESCRIPTION "Ph-N Voltage V2 (1/100 V)"
                ::= { minInstantaneousEntry 110062 } 
minInstVoltPhNV2Date   OBJECT-TYPE
                SYNTAX      Unsigned32
                MAX-ACCESS  read-only
                STATUS      current
                DESCRIPTION "Ph-N Voltage V2 Date"
                ::= { minInstantaneousEntry 110063 }
minInstVoltPhNV3   OBJECT-TYPE
                SYNTAX      Unsigned32
                MAX-ACCESS  read-only
                STATUS      current
                DESCRIPTION "Ph-N Voltage V3 (1/100 V)"
                ::= { minInstantaneousEntry 110064 } 
minInstVoltPhNV3Date   OBJECT-TYPE
                SYNTAX      Unsigned32
                MAX-ACCESS  read-only
                STATUS      current
                DESCRIPTION "Ph-N Voltage V3Date"
                ::= { minInstantaneousEntry 110065 }
minInstVoltPhNVn   OBJECT-TYPE
                SYNTAX      Unsigned32
                MAX-ACCESS  read-only
                STATUS      current
                DESCRIPTION "Ph-N Voltage Vn (1/100 V)"
                ::= { minInstantaneousEntry 110066 }
minInstVoltPhNVnDate   OBJECT-TYPE
                SYNTAX      Unsigned32
                MAX-ACCESS  read-only
                STATUS      current
                DESCRIPTION "Ph-N Voltage Vn Date"
                ::= { minInstantaneousEntry 110067 }  
minInstVoltPhPhU12   OBJECT-TYPE
                SYNTAX      Unsigned32
                MAX-ACCESS  read-only
                STATUS      current
                DESCRIPTION "Ph-Ph Voltage U12 (1/100 V)"
                ::= { minInstantaneousEntry 110070 }  
minInstVoltPhPhU12Date   OBJECT-TYPE
                SYNTAX      Unsigned32
                MAX-ACCESS  read-only
                STATUS      current
                DESCRIPTION "Ph-Ph Voltage U12 Date"
                ::= { minInstantaneousEntry 110071 } 
minInstVoltPhPhU23   OBJECT-TYPE
                SYNTAX      Unsigned32
                MAX-ACCESS  read-only
                STATUS      current
                DESCRIPTION "Ph-Ph Voltage U23 (1/100 V)"
                ::= { minInstantaneousEntry 110072 }  
minInstVoltPhPhU23Date   OBJECT-TYPE
                SYNTAX      Unsigned32
                MAX-ACCESS  read-only
                STATUS      current
                DESCRIPTION "Ph-Ph Voltage U23 Date"
                ::= { minInstantaneousEntry 110073 } 
minInstVoltPhPhU31   OBJECT-TYPE
                SYNTAX      Unsigned32
                MAX-ACCESS  read-only
                STATUS      current
                DESCRIPTION "Ph-Ph Voltage U31 (1/100 V)"
                ::= { minInstantaneousEntry 110074 }  
minInstVoltPhPhU31Date   OBJECT-TYPE
                SYNTAX      Unsigned32
                MAX-ACCESS  read-only
                STATUS      current
                DESCRIPTION "Ph-Ph Voltage U31 Date"
                ::= { minInstantaneousEntry 110075 } 

-- *******************
-- ** Current ********
-- *******************
minInstCurrentI1   OBJECT-TYPE
                SYNTAX      Unsigned32
                MAX-ACCESS  read-only
                STATUS      current
                DESCRIPTION "Current I1 (mA)"
                ::= { minInstantaneousEntry 10046 }
minInstCurrentI1Date   OBJECT-TYPE
                SYNTAX      Unsigned32
                MAX-ACCESS  read-only
                STATUS      current
                DESCRIPTION "Current I1 Date"
                ::= { minInstantaneousEntry 10047 }
minInstCurrentI2   OBJECT-TYPE
                SYNTAX      Unsigned32
                MAX-ACCESS  read-only
                STATUS      current
                DESCRIPTION "Current I2 (mA)"
                ::= { minInstantaneousEntry 10048 }
minInstCurrentI2Date   OBJECT-TYPE
                SYNTAX      Unsigned32
                MAX-ACCESS  read-only
                STATUS      current
                DESCRIPTION "Current I2 Date"
                ::= { minInstantaneousEntry 10049 }
minInstCurrentI3   OBJECT-TYPE
                SYNTAX      Unsigned32
                MAX-ACCESS  read-only
                STATUS      current
                DESCRIPTION "Current I3 (mA)"
                ::= { minInstantaneousEntry 10050 }
minInstCurrentI3Date   OBJECT-TYPE
                SYNTAX      Unsigned32
                MAX-ACCESS  read-only
                STATUS      current
                DESCRIPTION "Current I3 Date"
                ::= { minInstantaneousEntry 10051 }    
minInstCurrentIn   OBJECT-TYPE
                SYNTAX      Unsigned32
                MAX-ACCESS  read-only
                STATUS      current
                DESCRIPTION "Current In (mA)"
                ::= { minInstantaneousEntry 10052 }
minInstCurrentInDate   OBJECT-TYPE
                SYNTAX      Unsigned32
                MAX-ACCESS  read-only
                STATUS      current
                DESCRIPTION "Current In Date"
                ::= { minInstantaneousEntry 10053 }

-- *******************
-- ** Total Power ****
-- *******************
minInstTotalPowerActive   OBJECT-TYPE
                SYNTAX      Integer32
                MAX-ACCESS  read-only
                STATUS      current
                DESCRIPTION "Total Active Power (W)"
                ::= { minInstantaneousEntry 80062 }
minInstTotalPowerActiveDate   OBJECT-TYPE
                SYNTAX      Unsigned32
                MAX-ACCESS  read-only
                STATUS      current
                DESCRIPTION "Total Active Power Date"
                ::= { minInstantaneousEntry 80063 }
minInstTotalPowerReactive   OBJECT-TYPE
                SYNTAX      Integer32
                MAX-ACCESS  read-only
                STATUS      current
                DESCRIPTION "Total Reactive Power (var)"
                ::= { minInstantaneousEntry 80070 }
minInstTotalPowerReactiveDate   OBJECT-TYPE
                SYNTAX      Unsigned32
                MAX-ACCESS  read-only
                STATUS      current
                DESCRIPTION "Total Reactive Power Date"
                ::= { minInstantaneousEntry 80071 }
minInstTotalPowerApparent   OBJECT-TYPE
                SYNTAX      Unsigned32
                MAX-ACCESS  read-only
                STATUS      current
                DESCRIPTION "Total Apparent Power (VA)"
                ::= { minInstantaneousEntry 80086 }
minInstTotalPowerApparentDate   OBJECT-TYPE
                SYNTAX      Unsigned32
                MAX-ACCESS  read-only
                STATUS      current
                DESCRIPTION "Total Apparent Power Date"
                ::= { minInstantaneousEntry 80087 }
minInstTotalPowerFactor   OBJECT-TYPE
                SYNTAX      Integer32
                MAX-ACCESS  read-only
                STATUS      current
                DESCRIPTION "Total Power Factor (1/1000)"
                ::= { minInstantaneousEntry 75022 }
minInstTotalPowerFactorType   OBJECT-TYPE
                SYNTAX      Unsigned32
                MAX-ACCESS  read-only
                STATUS      current
                DESCRIPTION "Total Power Factor Type (1=Leading ; 2=Lagging)"
                ::= { minInstantaneousEntry 75027 }
minInstTotalPowerFactorDate   OBJECT-TYPE
                SYNTAX      Unsigned32
                MAX-ACCESS  read-only
                STATUS      current
                DESCRIPTION "Total Power Factor Date"
                ::= { minInstantaneousEntry 75023 }

-- *******************
-- ** Phasis Power ***
-- *******************
minInstPowerActiveP1   OBJECT-TYPE
                SYNTAX      Integer32
                MAX-ACCESS  read-only
                STATUS      current
                DESCRIPTION "P1 Active Power (W)"
                ::= { minInstantaneousEntry 80056 }
minInstPowerActiveP1Date   OBJECT-TYPE
                SYNTAX      Unsigned32
                MAX-ACCESS  read-only
                STATUS      current
                DESCRIPTION "P1 Active Power Date"
                ::= { minInstantaneousEntry 80057 }
minInstPowerActiveP2   OBJECT-TYPE
                SYNTAX      Integer32
                MAX-ACCESS  read-only
                STATUS      current
                DESCRIPTION "P2 Active Power (W)"
                ::= { minInstantaneousEntry 80058 }
minInstPowerActiveP2Date   OBJECT-TYPE
                SYNTAX      Unsigned32
                MAX-ACCESS  read-only
                STATUS      current
                DESCRIPTION "P2 Active Power Date"
                ::= { minInstantaneousEntry 80059 } 
minInstPowerActiveP3   OBJECT-TYPE
                SYNTAX      Integer32
                MAX-ACCESS  read-only
                STATUS      current
                DESCRIPTION "P3 Active Power (W)"
                ::= { minInstantaneousEntry 80060 }
minInstPowerActiveP3Date   OBJECT-TYPE
                SYNTAX      Unsigned32
                MAX-ACCESS  read-only
                STATUS      current
                DESCRIPTION "P3 Active Power Date"
                ::= { minInstantaneousEntry 80061 } 
minInstPowerReactiveQ1   OBJECT-TYPE
                SYNTAX      Integer32
                MAX-ACCESS  read-only
                STATUS      current
                DESCRIPTION "Q1 Reactive Power (var)"
                ::= { minInstantaneousEntry 80064 } 
minInstPowerReactiveQ1Date   OBJECT-TYPE
                SYNTAX      Unsigned32
                MAX-ACCESS  read-only
                STATUS      current
                DESCRIPTION "Q1 Reactive Power Date"
                ::= { minInstantaneousEntry 80065 } 
minInstPowerReactiveQ2   OBJECT-TYPE
                SYNTAX      Integer32
                MAX-ACCESS  read-only
                STATUS      current
                DESCRIPTION "Q2 Reactive Power (var)"
                ::= { minInstantaneousEntry 80066 } 
minInstPowerReactiveQ2Date   OBJECT-TYPE
                SYNTAX      Unsigned32
                MAX-ACCESS  read-only
                STATUS      current
                DESCRIPTION "Q2 Reactive Power Date"
                ::= { minInstantaneousEntry 80067 }  
minInstPowerReactiveQ3   OBJECT-TYPE
                SYNTAX      Integer32
                MAX-ACCESS  read-only
                STATUS      current
                DESCRIPTION "Q3 Reactive Power (var)"
                ::= { minInstantaneousEntry 80068 } 
minInstPowerReactiveQ3Date   OBJECT-TYPE
                SYNTAX      Unsigned32
                MAX-ACCESS  read-only
                STATUS      current
                DESCRIPTION "Q3 Reactive Power Date"
                ::= { minInstantaneousEntry 80069 }  
minInstPowerApparentS1   OBJECT-TYPE
                SYNTAX      Unsigned32
                MAX-ACCESS  read-only
                STATUS      current
                DESCRIPTION "S1 Apparent Power (VA)"
                ::= { minInstantaneousEntry 80080 }  
minInstPowerApparentS1Date   OBJECT-TYPE
                SYNTAX      Unsigned32
                MAX-ACCESS  read-only
                STATUS      current
                DESCRIPTION "S1 Apparent Power Date"
                ::= { minInstantaneousEntry 80081 } 
minInstPowerApparentS2   OBJECT-TYPE
                SYNTAX      Unsigned32
                MAX-ACCESS  read-only
                STATUS      current
                DESCRIPTION "S2 Apparent Power (VA)"
                ::= { minInstantaneousEntry 80082 }  
minInstPowerApparentS2Date   OBJECT-TYPE
                SYNTAX      Unsigned32
                MAX-ACCESS  read-only
                STATUS      current
                DESCRIPTION "S2 Apparent Power Date"
                ::= { minInstantaneousEntry 80083 } 
minInstPowerApparentS3   OBJECT-TYPE
                SYNTAX      Unsigned32
                MAX-ACCESS  read-only
                STATUS      current
                DESCRIPTION "S3 Apparent Power (VA)"
                ::= { minInstantaneousEntry 80084 }  
minInstPowerApparentS3Date   OBJECT-TYPE
                SYNTAX      Unsigned32
                MAX-ACCESS  read-only
                STATUS      current
                DESCRIPTION "S3 Apparent Power Date"
                ::= { minInstantaneousEntry 80085 } 

-- *******************
-- ** Power Factor ***
-- *******************
minInstPowerFactorPF1   OBJECT-TYPE
                SYNTAX      Integer32
                MAX-ACCESS  read-only
                STATUS      current
                DESCRIPTION "PF1 Power Factor (1/1000)"
                ::= { minInstantaneousEntry 75016 }
minInstPowerFactorTypeSPF1   OBJECT-TYPE
                SYNTAX      Unsigned32
                MAX-ACCESS  read-only
                STATUS      current
                DESCRIPTION "sPF1 Power Factor Type (1=Leading ; 2=Lagging)"
                ::= { minInstantaneousEntry 75024 }
minInstPowerFactorPF1Date   OBJECT-TYPE
                SYNTAX      Unsigned32
                MAX-ACCESS  read-only
                STATUS      current
                DESCRIPTION "PF1 Power Factor Date"
                ::= { minInstantaneousEntry 75017}
minInstPowerFactorPF2   OBJECT-TYPE
                SYNTAX      Integer32
                MAX-ACCESS  read-only
                STATUS      current
                DESCRIPTION "PF2 Power Factor (1/1000)"
                ::= { minInstantaneousEntry 75018 }
minInstPowerFactorTypeSPF2   OBJECT-TYPE
                SYNTAX      Unsigned32
                MAX-ACCESS  read-only
                STATUS      current
                DESCRIPTION "sPF1 Power Factor Type (1=Leading ; 2=Lagging)"
                ::= { minInstantaneousEntry 75025 }
minInstPowerFactorPF2Date   OBJECT-TYPE
                SYNTAX      Unsigned32
                MAX-ACCESS  read-only
                STATUS      current
                DESCRIPTION "PF2 Power Factor Date"
                ::= { minInstantaneousEntry 75019 }
minInstPowerFactorPF3   OBJECT-TYPE
                SYNTAX      Integer32
                MAX-ACCESS  read-only
                STATUS      current
                DESCRIPTION "PF3 Power Factor (1/1000)"
                ::= { minInstantaneousEntry 75020 }
minInstPowerFactorTypeSPF3   OBJECT-TYPE
                SYNTAX      Unsigned32
                MAX-ACCESS  read-only
                STATUS      current
                DESCRIPTION "sPF1 Power Factor Type (1=Leading ; 2=Lagging)"
                ::= { minInstantaneousEntry 75026 }
minInstPowerFactorPF3Date   OBJECT-TYPE
                SYNTAX      Unsigned32
                MAX-ACCESS  read-only
                STATUS      current
                DESCRIPTION "PF3 Power Factor Date"
                ::= { minInstantaneousEntry 75021 }

-- *******************************************************************************
-- ********************* MAX AVERAGES TABLE **************************************
maxAveragesTable       OBJECT-TYPE
                SYNTAX      SEQUENCE OF SeqMaxAveragesEnt
                MAX-ACCESS  not-accessible
                STATUS      current
                DESCRIPTION "Measurement Table of Max Averages Data"
                ::= { productMetrology 60 }

maxAveragesEntry       OBJECT-TYPE
                SYNTAX      SeqMaxAveragesEnt
                MAX-ACCESS  not-accessible
                STATUS      current
                DESCRIPTION "Max Averages Data Table for given Product Index and Load Index"
                INDEX  { maxAvgModbusAddress, maxAvgLoadIndex  }
                ::= { maxAveragesTable 1 }

maxAvgModbusAddress    OBJECT-TYPE
                SYNTAX      Unsigned32(1..255)
                MAX-ACCESS  read-only
                STATUS      current
                DESCRIPTION "Modbus address of the product"
                ::= { maxAveragesEntry 1 }

maxAvgProductIndex    OBJECT-TYPE
                SYNTAX      Unsigned32(1..33)  -- 32 Products + 1 Gateway
                MAX-ACCESS  read-only
                STATUS      current
                DESCRIPTION "Index of the Product to reach (1 = Gateway itself)"
                ::= { maxAveragesEntry 5 }

maxAvgLoadIndex       OBJECT-TYPE
                SYNTAX      Unsigned32(1..16)  -- 6 Loads + 10 MultiFluids
                MAX-ACCESS  read-only
                STATUS      current
                DESCRIPTION "Index of the Load to reach"
                ::= { maxAveragesEntry 6 }

maxAvgLoadRowStatus      OBJECT-TYPE
                SYNTAX       RowStatus
                MAX-ACCESS   read-create
                STATUS       current
                DESCRIPTION "The status of this conceptual row."
                ::= { maxAveragesEntry 10 }

-- *******************
-- ** System *********
-- *******************
maxAvgFrequency   OBJECT-TYPE
                SYNTAX      Unsigned32
                MAX-ACCESS  read-only
                STATUS      current
                DESCRIPTION "System Frequency (mHz)"
                ::= { maxAveragesEntry 40010 }
maxAvgFrequencyDate   OBJECT-TYPE
                SYNTAX      Unsigned32
                MAX-ACCESS  read-only
                STATUS      current
                DESCRIPTION "System Frequency Date"
                ::= { maxAveragesEntry 40011 }
                
-- *******************
-- ** Voltage ********
-- *******************
maxAvgVoltPhNV1   OBJECT-TYPE
                SYNTAX      Unsigned32
                MAX-ACCESS  read-only
                STATUS      current
                DESCRIPTION "Ph-N Voltage V1 (1/100 V)"
                ::= { maxAveragesEntry 110175 } 
maxAvgVoltPhNV1Date   OBJECT-TYPE
                SYNTAX      Unsigned32
                MAX-ACCESS  read-only
                STATUS      current
                DESCRIPTION "Ph-N Voltage V1 Date"
                ::= { maxAveragesEntry 110176 }
maxAvgVoltPhNV2   OBJECT-TYPE
                SYNTAX      Unsigned32
                MAX-ACCESS  read-only
                STATUS      current
                DESCRIPTION "Ph-N Voltage V2 (1/100 V)"
                ::= { maxAveragesEntry 110177 } 
maxAvgVoltPhNV2Date   OBJECT-TYPE
                SYNTAX      Unsigned32
                MAX-ACCESS  read-only
                STATUS      current
                DESCRIPTION "Ph-N Voltage V2 Date"
                ::= { maxAveragesEntry 110178 }
maxAvgVoltPhNV3   OBJECT-TYPE
                SYNTAX      Unsigned32
                MAX-ACCESS  read-only
                STATUS      current
                DESCRIPTION "Ph-N Voltage V3 (1/100 V)"
                ::= { maxAveragesEntry 110179 } 
maxAvgVoltPhNV3Date   OBJECT-TYPE
                SYNTAX      Unsigned32
                MAX-ACCESS  read-only
                STATUS      current
                DESCRIPTION "Ph-N Voltage V3Date"
                ::= { maxAveragesEntry 110180 }
maxAvgVoltPhNVn   OBJECT-TYPE
                SYNTAX      Unsigned32
                MAX-ACCESS  read-only
                STATUS      current
                DESCRIPTION "Ph-N Voltage Vn (1/100 V)"
                ::= { maxAveragesEntry 110181 }
maxAvgVoltPhNVnDate   OBJECT-TYPE
                SYNTAX      Unsigned32
                MAX-ACCESS  read-only
                STATUS      current
                DESCRIPTION "Ph-N Voltage Vn Date"
                ::= { maxAveragesEntry 110182 }  
maxAvgVoltPhPhU12   OBJECT-TYPE
                SYNTAX      Unsigned32
                MAX-ACCESS  read-only
                STATUS      current
                DESCRIPTION "Ph-Ph Voltage U12 (1/100 V)"
                ::= { maxAveragesEntry 110185 }  
maxAvgVoltPhPhU12Date   OBJECT-TYPE
                SYNTAX      Unsigned32
                MAX-ACCESS  read-only
                STATUS      current
                DESCRIPTION "Ph-Ph Voltage U12 Date"
                ::= { maxAveragesEntry 110186 } 
maxAvgVoltPhPhU23   OBJECT-TYPE
                SYNTAX      Unsigned32
                MAX-ACCESS  read-only
                STATUS      current
                DESCRIPTION "Ph-Ph Voltage U23 (1/100 V)"
                ::= { maxAveragesEntry 110187 }  
maxAvgVoltPhPhU23Date   OBJECT-TYPE
                SYNTAX      Unsigned32
                MAX-ACCESS  read-only
                STATUS      current
                DESCRIPTION "Ph-Ph Voltage U23 Date"
                ::= { maxAveragesEntry 110188 } 
maxAvgVoltPhPhU31   OBJECT-TYPE
                SYNTAX      Unsigned32
                MAX-ACCESS  read-only
                STATUS      current
                DESCRIPTION "Ph-Ph Voltage U31 (1/100 V)"
                ::= { maxAveragesEntry 110189 }  
maxAvgVoltPhPhU31Date   OBJECT-TYPE
                SYNTAX      Unsigned32
                MAX-ACCESS  read-only
                STATUS      current
                DESCRIPTION "Ph-Ph Voltage U31 Date"
                ::= { maxAveragesEntry 110190 } 

-- *******************
-- ** Current ********
-- *******************
maxAvgCurrentI1   OBJECT-TYPE
                SYNTAX      Unsigned32
                MAX-ACCESS  read-only
                STATUS      current
                DESCRIPTION "Current I1 (mA)"
                ::= { maxAveragesEntry 10129 }
maxAvgCurrentI1Date   OBJECT-TYPE
                SYNTAX      Unsigned32
                MAX-ACCESS  read-only
                STATUS      current
                DESCRIPTION "Current I1 Date"
                ::= { maxAveragesEntry 10130 }
maxAvgCurrentI2   OBJECT-TYPE
                SYNTAX      Unsigned32
                MAX-ACCESS  read-only
                STATUS      current
                DESCRIPTION "Current I2 (mA)"
                ::= { maxAveragesEntry 10131 }
maxAvgCurrentI2Date   OBJECT-TYPE
                SYNTAX      Unsigned32
                MAX-ACCESS  read-only
                STATUS      current
                DESCRIPTION "Current I2 Date"
                ::= { maxAveragesEntry 10132 }
maxAvgCurrentI3   OBJECT-TYPE
                SYNTAX      Unsigned32
                MAX-ACCESS  read-only
                STATUS      current
                DESCRIPTION "Current I3 (mA)"
                ::= { maxAveragesEntry 10133 }
maxAvgCurrentI3Date   OBJECT-TYPE
                SYNTAX      Unsigned32
                MAX-ACCESS  read-only
                STATUS      current
                DESCRIPTION "Current I3 Date"
                ::= { maxAveragesEntry 10134 }    
maxAvgCurrentIn   OBJECT-TYPE
                SYNTAX      Unsigned32
                MAX-ACCESS  read-only
                STATUS      current
                DESCRIPTION "Current In (mA)"
                ::= { maxAveragesEntry 10135 }
maxAvgCurrentInDate   OBJECT-TYPE
                SYNTAX      Unsigned32
                MAX-ACCESS  read-only
                STATUS      current
                DESCRIPTION "Current In Date"
                ::= { maxAveragesEntry 10136 }

-- *******************
-- ** Total Power ****
-- *******************
maxAvgTotalPowerActive   OBJECT-TYPE
                SYNTAX      Integer32
                MAX-ACCESS  read-only
                STATUS      current
                DESCRIPTION "Total Active Power (W)"
                ::= { maxAveragesEntry 80182 }
maxAvgTotalPowerActiveDate   OBJECT-TYPE
                SYNTAX      Unsigned32
                MAX-ACCESS  read-only
                STATUS      current
                DESCRIPTION "Total Active Power Date"
                ::= { maxAveragesEntry 80183 }
maxAvgTotalPowerReactive   OBJECT-TYPE
                SYNTAX      Integer32
                MAX-ACCESS  read-only
                STATUS      current
                DESCRIPTION "Total Reactive Power (var)"
                ::= { maxAveragesEntry 80190 }
maxAvgTotalPowerReactiveDate   OBJECT-TYPE
                SYNTAX      Unsigned32
                MAX-ACCESS  read-only
                STATUS      current
                DESCRIPTION "Total Reactive Power Date"
                ::= { maxAveragesEntry 80191 }
maxAvgTotalPowerApparent   OBJECT-TYPE
                SYNTAX      Unsigned32
                MAX-ACCESS  read-only
                STATUS      current
                DESCRIPTION "Total Apparent Power (VA)"
                ::= { maxAveragesEntry 80206 }
maxAvgTotalPowerApparentDate   OBJECT-TYPE
                SYNTAX      Unsigned32
                MAX-ACCESS  read-only
                STATUS      current
                DESCRIPTION "Total Apparent Power Date"
                ::= { maxAveragesEntry 80207 }
maxAvgTotalPowerFactor   OBJECT-TYPE
                SYNTAX      Integer32
                MAX-ACCESS  read-only
                STATUS      current
                DESCRIPTION "Total Power Factor (1/1000)"
                ::= { maxAveragesEntry 75058 }
maxAvgTotalPowerFactorType   OBJECT-TYPE
                SYNTAX      Unsigned32
                MAX-ACCESS  read-only
                STATUS      current
                DESCRIPTION "Total Power Factor Type (1=Leading ; 2=Lagging)"
                ::= { maxAveragesEntry 75063 }
maxAvgTotalPowerFactorDate   OBJECT-TYPE
                SYNTAX      Unsigned32
                MAX-ACCESS  read-only
                STATUS      current
                DESCRIPTION "Total Power Factor Date"
                ::= { maxAveragesEntry 75059 }

-- *******************
-- ** Phasis Power ***
-- *******************
maxAvgPowerActiveP1   OBJECT-TYPE
                SYNTAX      Integer32
                MAX-ACCESS  read-only
                STATUS      current
                DESCRIPTION "P1 Active Power (W)"
                ::= { maxAveragesEntry 80176 }
maxAvgPowerActiveP1Date   OBJECT-TYPE
                SYNTAX      Unsigned32
                MAX-ACCESS  read-only
                STATUS      current
                DESCRIPTION "P1 Active Power Date"
                ::= { maxAveragesEntry 80177 }
maxAvgPowerActiveP2   OBJECT-TYPE
                SYNTAX      Integer32
                MAX-ACCESS  read-only
                STATUS      current
                DESCRIPTION "P2 Active Power (W)"
                ::= { maxAveragesEntry 80178 }
maxAvgPowerActiveP2Date   OBJECT-TYPE
                SYNTAX      Unsigned32
                MAX-ACCESS  read-only
                STATUS      current
                DESCRIPTION "P2 Active Power Date"
                ::= { maxAveragesEntry 80179 } 
maxAvgPowerActiveP3   OBJECT-TYPE
                SYNTAX      Integer32
                MAX-ACCESS  read-only
                STATUS      current
                DESCRIPTION "P3 Active Power (W)"
                ::= { maxAveragesEntry 80180 }
maxAvgPowerActiveP3Date   OBJECT-TYPE
                SYNTAX      Unsigned32
                MAX-ACCESS  read-only
                STATUS      current
                DESCRIPTION "P3 Active Power Date"
                ::= { maxAveragesEntry 80181 } 
maxAvgPowerReactiveQ1   OBJECT-TYPE
                SYNTAX      Integer32
                MAX-ACCESS  read-only
                STATUS      current
                DESCRIPTION "Q1 Reactive Power (var)"
                ::= { maxAveragesEntry 80184 } 
maxAvgPowerReactiveQ1Date   OBJECT-TYPE
                SYNTAX      Unsigned32
                MAX-ACCESS  read-only
                STATUS      current
                DESCRIPTION "Q1 Reactive Power Date"
                ::= { maxAveragesEntry 80185 } 
maxAvgPowerReactiveQ2   OBJECT-TYPE
                SYNTAX      Integer32
                MAX-ACCESS  read-only
                STATUS      current
                DESCRIPTION "Q2 Reactive Power (var)"
                ::= { maxAveragesEntry 80186 } 
maxAvgPowerReactiveQ2Date   OBJECT-TYPE
                SYNTAX      Unsigned32
                MAX-ACCESS  read-only
                STATUS      current
                DESCRIPTION "Q2 Reactive Power Date"
                ::= { maxAveragesEntry 80187 }  
maxAvgPowerReactiveQ3   OBJECT-TYPE
                SYNTAX      Integer32
                MAX-ACCESS  read-only
                STATUS      current
                DESCRIPTION "Q3 Reactive Power (var)"
                ::= { maxAveragesEntry 80188 } 
maxAvgPowerReactiveQ3Date   OBJECT-TYPE
                SYNTAX      Unsigned32
                MAX-ACCESS  read-only
                STATUS      current
                DESCRIPTION "Q3 Reactive Power Date"
                ::= { maxAveragesEntry 80189 }  
maxAvgPowerApparentS1   OBJECT-TYPE
                SYNTAX      Unsigned32
                MAX-ACCESS  read-only
                STATUS      current
                DESCRIPTION "S1 Apparent Power (VA)"
                ::= { maxAveragesEntry 80200 }  
maxAvgPowerApparentS1Date   OBJECT-TYPE
                SYNTAX      Unsigned32
                MAX-ACCESS  read-only
                STATUS      current
                DESCRIPTION "S1 Apparent Power Date"
                ::= { maxAveragesEntry 80201 } 
maxAvgPowerApparentS2   OBJECT-TYPE
                SYNTAX      Unsigned32
                MAX-ACCESS  read-only
                STATUS      current
                DESCRIPTION "S2 Apparent Power (VA)"
                ::= { maxAveragesEntry 80202 }  
maxAvgPowerApparentS2Date   OBJECT-TYPE
                SYNTAX      Unsigned32
                MAX-ACCESS  read-only
                STATUS      current
                DESCRIPTION "S2 Apparent Power Date"
                ::= { maxAveragesEntry 80203 } 
maxAvgPowerApparentS3   OBJECT-TYPE
                SYNTAX      Unsigned32
                MAX-ACCESS  read-only
                STATUS      current
                DESCRIPTION "S3 Apparent Power (VA)"
                ::= { maxAveragesEntry 80204 }  
maxAvgPowerApparentS3Date   OBJECT-TYPE
                SYNTAX      Unsigned32
                MAX-ACCESS  read-only
                STATUS      current
                DESCRIPTION "S3 Apparent Power Date"
                ::= { maxAveragesEntry 80205 } 

-- *******************
-- ** Power Factor ***
-- *******************
maxAvgPowerFactorPF1   OBJECT-TYPE
                SYNTAX      Integer32
                MAX-ACCESS  read-only
                STATUS      current
                DESCRIPTION "PF1 Power Factor (1/1000)"
                ::= { maxAveragesEntry 75052 }
maxAvgPowerFactorTypeSPF1   OBJECT-TYPE
                SYNTAX      Unsigned32
                MAX-ACCESS  read-only
                STATUS      current
                DESCRIPTION "sPF1 Power Factor Type (1=Leading ; 2=Lagging)"
                ::= { maxAveragesEntry 75060 }
maxAvgPowerFactorPF1Date   OBJECT-TYPE
                SYNTAX      Unsigned32
                MAX-ACCESS  read-only
                STATUS      current
                DESCRIPTION "PF1 Power Factor Date"
                ::= { maxAveragesEntry 75053 }
maxAvgPowerFactorPF2   OBJECT-TYPE
                SYNTAX      Integer32
                MAX-ACCESS  read-only
                STATUS      current
                DESCRIPTION "PF2 Power Factor (1/1000)"
                ::= { maxAveragesEntry 75054 }
maxAvgPowerFactorTypeSPF2   OBJECT-TYPE
                SYNTAX      Unsigned32
                MAX-ACCESS  read-only
                STATUS      current
                DESCRIPTION "sPF1 Power Factor Type (1=Leading ; 2=Lagging)"
                ::= { maxAveragesEntry 75061 }
maxAvgPowerFactorPF2Date   OBJECT-TYPE
                SYNTAX      Unsigned32
                MAX-ACCESS  read-only
                STATUS      current
                DESCRIPTION "PF2 Power Factor Date"
                ::= { maxAveragesEntry 75055 }
maxAvgPowerFactorPF3   OBJECT-TYPE
                SYNTAX      Integer32
                MAX-ACCESS  read-only
                STATUS      current
                DESCRIPTION "PF3 Power Factor (1/1000)"
                ::= { maxAveragesEntry 75056 }
maxAvgPowerFactorTypeSPF3   OBJECT-TYPE
                SYNTAX      Unsigned32
                MAX-ACCESS  read-only
                STATUS      current
                DESCRIPTION "sPF1 Power Factor Type (1=Leading ; 2=Lagging)"
                ::= { maxAveragesEntry 75062 }
maxAvgPowerFactorPF3Date   OBJECT-TYPE
                SYNTAX      Unsigned32
                MAX-ACCESS  read-only
                STATUS      current
                DESCRIPTION "PF3 Power Factor Date"
                ::= { maxAveragesEntry 75057 }

-- *******************************************************************************
-- ********************* MIN AVERAGES TABLE **************************************
minAveragesTable       OBJECT-TYPE
                SYNTAX      SEQUENCE OF SeqMinAveragesEnt
                MAX-ACCESS  not-accessible
                STATUS      current
                DESCRIPTION "Min Averages Metrology Table"
                ::= { productMetrology 70 }

minAveragesEntry       OBJECT-TYPE
                SYNTAX      SeqMinAveragesEnt
                MAX-ACCESS  not-accessible
                STATUS      current
                DESCRIPTION "Min Averages Data Table for given Product Index and Load Index"
                INDEX  { minAvgModbusAddress, minAvgLoadIndex  }
                ::= { minAveragesTable 1 }

minAvgModbusAddress    OBJECT-TYPE
                SYNTAX      Unsigned32(1..255)
                MAX-ACCESS  read-only
                STATUS      current
                DESCRIPTION "Modbus address of the product"
                ::= { minAveragesEntry 1 }

minAvgProductIndex    OBJECT-TYPE
                SYNTAX      Unsigned32(1..33)  -- 32 Products + 1 Gateway
                MAX-ACCESS  read-only
                STATUS      current
                DESCRIPTION "Index of the Product to reach (1 = Gateway itself)"
                ::= { minAveragesEntry 5 }

minAvgLoadIndex       OBJECT-TYPE
                SYNTAX      Unsigned32(1..16)  -- 6 Loads + 10 MultiFluids
                MAX-ACCESS  read-only
                STATUS      current
                DESCRIPTION "Index of the Load to reach"
                ::= { minAveragesEntry 6 }

minAvgLoadRowStatus      OBJECT-TYPE
                SYNTAX       RowStatus
                MAX-ACCESS   read-create
                STATUS       current
                DESCRIPTION "The status of this conceptual row."
                ::= { minAveragesEntry 10 }

-- *******************
-- ** System *********
-- *******************
minAvgFrequency   OBJECT-TYPE
                SYNTAX      Unsigned32
                MAX-ACCESS  read-only
                STATUS      current
                DESCRIPTION "System Frequency (mHz)"
                ::= { minAveragesEntry 40012 }
minAvgFrequencyDate   OBJECT-TYPE
                SYNTAX      Unsigned32
                MAX-ACCESS  read-only
                STATUS      current
                DESCRIPTION "System Frequency Date"
                ::= { minAveragesEntry 40013 }
                
-- *******************
-- ** Voltage ********
-- *******************
minAvgVoltPhNV1   OBJECT-TYPE
                SYNTAX      Unsigned32
                MAX-ACCESS  read-only
                STATUS      current
                DESCRIPTION "Ph-N Voltage V1 (1/100 V)"
                ::= { minAveragesEntry 110136 } 
minAvgVoltPhNV1Date   OBJECT-TYPE
                SYNTAX      Unsigned32
                MAX-ACCESS  read-only
                STATUS      current
                DESCRIPTION "Ph-N Voltage V1 Date"
                ::= { minAveragesEntry 110137 }
minAvgVoltPhNV2   OBJECT-TYPE
                SYNTAX      Unsigned32
                MAX-ACCESS  read-only
                STATUS      current
                DESCRIPTION "Ph-N Voltage V2 (1/100 V)"
                ::= { minAveragesEntry 110138 } 
minAvgVoltPhNV2Date   OBJECT-TYPE
                SYNTAX      Unsigned32
                MAX-ACCESS  read-only
                STATUS      current
                DESCRIPTION "Ph-N Voltage V2 Date"
                ::= { minAveragesEntry 110139 }
minAvgVoltPhNV3   OBJECT-TYPE
                SYNTAX      Unsigned32
                MAX-ACCESS  read-only
                STATUS      current
                DESCRIPTION "Ph-N Voltage V3 (1/100 V)"
                ::= { minAveragesEntry 110140 } 
minAvgVoltPhNV3Date   OBJECT-TYPE
                SYNTAX      Unsigned32
                MAX-ACCESS  read-only
                STATUS      current
                DESCRIPTION "Ph-N Voltage V3Date"
                ::= { minAveragesEntry 110141 }
minAvgVoltPhNVn   OBJECT-TYPE
                SYNTAX      Unsigned32
                MAX-ACCESS  read-only
                STATUS      current
                DESCRIPTION "Ph-N Voltage Vn (1/100 V)"
                ::= { minAveragesEntry 110142 }
minAvgVoltPhNVnDate   OBJECT-TYPE
                SYNTAX      Unsigned32
                MAX-ACCESS  read-only
                STATUS      current
                DESCRIPTION "Ph-N Voltage Vn Date"
                ::= { minAveragesEntry 110143 }  
minAvgVoltPhPhU12   OBJECT-TYPE
                SYNTAX      Unsigned32
                MAX-ACCESS  read-only
                STATUS      current
                DESCRIPTION "Ph-Ph Voltage U12 (1/100 V)"
                ::= { minAveragesEntry 110146 }  
minAvgVoltPhPhU12Date   OBJECT-TYPE
                SYNTAX      Unsigned32
                MAX-ACCESS  read-only
                STATUS      current
                DESCRIPTION "Ph-Ph Voltage U12 Date"
                ::= { minAveragesEntry 110147 } 
minAvgVoltPhPhU23   OBJECT-TYPE
                SYNTAX      Unsigned32
                MAX-ACCESS  read-only
                STATUS      current
                DESCRIPTION "Ph-Ph Voltage U23 (1/100 V)"
                ::= { minAveragesEntry 110148 }  
minAvgVoltPhPhU23Date   OBJECT-TYPE
                SYNTAX      Unsigned32
                MAX-ACCESS  read-only
                STATUS      current
                DESCRIPTION "Ph-Ph Voltage U23 Date"
                ::= { minAveragesEntry 110149 } 
minAvgVoltPhPhU31   OBJECT-TYPE
                SYNTAX      Unsigned32
                MAX-ACCESS  read-only
                STATUS      current
                DESCRIPTION "Ph-Ph Voltage U31 (1/100 V)"
                ::= { minAveragesEntry 110150 }  
minAvgVoltPhPhU31Date   OBJECT-TYPE
                SYNTAX      Unsigned32
                MAX-ACCESS  read-only
                STATUS      current
                DESCRIPTION "Ph-Ph Voltage U31 Date"
                ::= { minAveragesEntry 110151 } 

-- *******************
-- ** Current ********
-- *******************
minAvgCurrentI1   OBJECT-TYPE
                SYNTAX      Unsigned32
                MAX-ACCESS  read-only
                STATUS      current
                DESCRIPTION "Current I1 (mA)"
                ::= { minAveragesEntry 10101 }
minAvgCurrentI1Date   OBJECT-TYPE
                SYNTAX      Unsigned32
                MAX-ACCESS  read-only
                STATUS      current
                DESCRIPTION "Current I1 Date"
                ::= { minAveragesEntry 10102 }
minAvgCurrentI2   OBJECT-TYPE
                SYNTAX      Unsigned32
                MAX-ACCESS  read-only
                STATUS      current
                DESCRIPTION "Current I2 (mA)"
                ::= { minAveragesEntry 10103 }
minAvgCurrentI2Date   OBJECT-TYPE
                SYNTAX      Unsigned32
                MAX-ACCESS  read-only
                STATUS      current
                DESCRIPTION "Current I2 Date"
                ::= { minAveragesEntry 10104 }
minAvgCurrentI3   OBJECT-TYPE
                SYNTAX      Unsigned32
                MAX-ACCESS  read-only
                STATUS      current
                DESCRIPTION "Current I3 (mA)"
                ::= { minAveragesEntry 10105 }
minAvgCurrentI3Date   OBJECT-TYPE
                SYNTAX      Unsigned32
                MAX-ACCESS  read-only
                STATUS      current
                DESCRIPTION "Current I3 Date"
                ::= { minAveragesEntry 10106 }    
minAvgCurrentIn   OBJECT-TYPE
                SYNTAX      Unsigned32
                MAX-ACCESS  read-only
                STATUS      current
                DESCRIPTION "Current In (mA)"
                ::= { minAveragesEntry 10107 }
minAvgCurrentInDate   OBJECT-TYPE
                SYNTAX      Unsigned32
                MAX-ACCESS  read-only
                STATUS      current
                DESCRIPTION "Current In Date"
                ::= { minAveragesEntry 10108 }

-- *******************
-- ** Total Power ****
-- *******************
minAvgTotalPowerActive   OBJECT-TYPE
                SYNTAX      Integer32
                MAX-ACCESS  read-only
                STATUS      current
                DESCRIPTION "Total Active Power (W)"
                ::= { minAveragesEntry 80142 }
minAvgTotalPowerActiveDate   OBJECT-TYPE
                SYNTAX      Unsigned32
                MAX-ACCESS  read-only
                STATUS      current
                DESCRIPTION "Total Active Power Date"
                ::= { minAveragesEntry 80143 }
minAvgTotalPowerReactive   OBJECT-TYPE
                SYNTAX      Integer32
                MAX-ACCESS  read-only
                STATUS      current
                DESCRIPTION "Total Reactive Power (var)"
                ::= { minAveragesEntry 80150 }
minAvgTotalPowerReactiveDate   OBJECT-TYPE
                SYNTAX      Unsigned32
                MAX-ACCESS  read-only
                STATUS      current
                DESCRIPTION "Total Reactive Power Date"
                ::= { minAveragesEntry 80151 }
minAvgTotalPowerApparent   OBJECT-TYPE
                SYNTAX      Unsigned32
                MAX-ACCESS  read-only
                STATUS      current
                DESCRIPTION "Total Apparent Power (VA)"
                ::= { minAveragesEntry 80166 }
minAvgTotalPowerApparentDate   OBJECT-TYPE
                SYNTAX      Unsigned32
                MAX-ACCESS  read-only
                STATUS      current
                DESCRIPTION "Total Apparent Power Date"
                ::= { minAveragesEntry 80167 }
minAvgTotalPowerFactor   OBJECT-TYPE
                SYNTAX      Integer32
                MAX-ACCESS  read-only
                STATUS      current
                DESCRIPTION "Total Power Factor (1/1000)"
                ::= { minAveragesEntry 75046 }
minAvgTotalPowerFactorType   OBJECT-TYPE
                SYNTAX      Unsigned32
                MAX-ACCESS  read-only
                STATUS      current
                DESCRIPTION "Total Power Factor Type (1=Leading ; 2=Lagging)"
                ::= { minAveragesEntry 75051 }
minAvgTotalPowerFactorDate   OBJECT-TYPE
                SYNTAX      Unsigned32
                MAX-ACCESS  read-only
                STATUS      current
                DESCRIPTION "Total Power Factor Date"
                ::= { minAveragesEntry 75047 }

-- *******************
-- ** Phasis Power ***
-- *******************
minAvgPowerActiveP1   OBJECT-TYPE
                SYNTAX      Integer32
                MAX-ACCESS  read-only
                STATUS      current
                DESCRIPTION "P1 Active Power (W)"
                ::= { minAveragesEntry 80136 }
minAvgPowerActiveP1Date   OBJECT-TYPE
                SYNTAX      Unsigned32
                MAX-ACCESS  read-only
                STATUS      current
                DESCRIPTION "P1 Active Power Date"
                ::= { minAveragesEntry 80137 }
minAvgPowerActiveP2   OBJECT-TYPE
                SYNTAX      Integer32
                MAX-ACCESS  read-only
                STATUS      current
                DESCRIPTION "P2 Active Power (W)"
                ::= { minAveragesEntry 80138 }
minAvgPowerActiveP2Date   OBJECT-TYPE
                SYNTAX      Unsigned32
                MAX-ACCESS  read-only
                STATUS      current
                DESCRIPTION "P2 Active Power Date"
                ::= { minAveragesEntry 80139 } 
minAvgPowerActiveP3   OBJECT-TYPE
                SYNTAX      Integer32
                MAX-ACCESS  read-only
                STATUS      current
                DESCRIPTION "P3 Active Power (W)"
                ::= { minAveragesEntry 80140 }
minAvgPowerActiveP3Date   OBJECT-TYPE
                SYNTAX      Unsigned32
                MAX-ACCESS  read-only
                STATUS      current
                DESCRIPTION "P3 Active Power Date"
                ::= { minAveragesEntry 80141 } 
minAvgPowerReactiveQ1   OBJECT-TYPE
                SYNTAX      Integer32
                MAX-ACCESS  read-only
                STATUS      current
                DESCRIPTION "Q1 Reactive Power (var)"
                ::= { minAveragesEntry 80144 } 
minAvgPowerReactiveQ1Date   OBJECT-TYPE
                SYNTAX      Unsigned32
                MAX-ACCESS  read-only
                STATUS      current
                DESCRIPTION "Q1 Reactive Power Date"
                ::= { minAveragesEntry 80145 } 
minAvgPowerReactiveQ2   OBJECT-TYPE
                SYNTAX      Integer32
                MAX-ACCESS  read-only
                STATUS      current
                DESCRIPTION "Q2 Reactive Power (var)"
                ::= { minAveragesEntry 80146 } 
minAvgPowerReactiveQ2Date   OBJECT-TYPE
                SYNTAX      Unsigned32
                MAX-ACCESS  read-only
                STATUS      current
                DESCRIPTION "Q2 Reactive Power Date"
                ::= { minAveragesEntry 80147 }  
minAvgPowerReactiveQ3   OBJECT-TYPE
                SYNTAX      Integer32
                MAX-ACCESS  read-only
                STATUS      current
                DESCRIPTION "Q3 Reactive Power (var)"
                ::= { minAveragesEntry 80148 } 
minAvgPowerReactiveQ3Date   OBJECT-TYPE
                SYNTAX      Unsigned32
                MAX-ACCESS  read-only
                STATUS      current
                DESCRIPTION "Q3 Reactive Power Date"
                ::= { minAveragesEntry 80149 }  
minAvgPowerApparentS1   OBJECT-TYPE
                SYNTAX      Unsigned32
                MAX-ACCESS  read-only
                STATUS      current
                DESCRIPTION "S1 Apparent Power (VA)"
                ::= { minAveragesEntry 80160 }  
minAvgPowerApparentS1Date   OBJECT-TYPE
                SYNTAX      Unsigned32
                MAX-ACCESS  read-only
                STATUS      current
                DESCRIPTION "S1 Apparent Power Date"
                ::= { minAveragesEntry 80161 } 
minAvgPowerApparentS2   OBJECT-TYPE
                SYNTAX      Unsigned32
                MAX-ACCESS  read-only
                STATUS      current
                DESCRIPTION "S2 Apparent Power (VA)"
                ::= { minAveragesEntry 80162 }  
minAvgPowerApparentS2Date   OBJECT-TYPE
                SYNTAX      Unsigned32
                MAX-ACCESS  read-only
                STATUS      current
                DESCRIPTION "S2 Apparent Power Date"
                ::= { minAveragesEntry 80163 } 
minAvgPowerApparentS3   OBJECT-TYPE
                SYNTAX      Unsigned32
                MAX-ACCESS  read-only
                STATUS      current
                DESCRIPTION "S3 Apparent Power (VA)"
                ::= { minAveragesEntry 80164 }  
minAvgPowerApparentS3Date   OBJECT-TYPE
                SYNTAX      Unsigned32
                MAX-ACCESS  read-only
                STATUS      current
                DESCRIPTION "S3 Apparent Power Date"
                ::= { minAveragesEntry 80165 } 

-- *******************
-- ** Power Factor ***
-- *******************
minAvgPowerFactorPF1   OBJECT-TYPE
                SYNTAX      Integer32
                MAX-ACCESS  read-only
                STATUS      current
                DESCRIPTION "PF1 Power Factor (1/1000)"
                ::= { minAveragesEntry 75040 }
minAvgPowerFactorTypeSPF1   OBJECT-TYPE
                SYNTAX      Unsigned32
                MAX-ACCESS  read-only
                STATUS      current
                DESCRIPTION "sPF1 Power Factor Type (1=Leading ; 2=Lagging)"
                ::= { minAveragesEntry 75048 }
minAvgPowerFactorPF1Date   OBJECT-TYPE
                SYNTAX      Unsigned32
                MAX-ACCESS  read-only
                STATUS      current
                DESCRIPTION "PF1 Power Factor Date"
                ::= { minAveragesEntry 75041 }
minAvgPowerFactorPF2   OBJECT-TYPE
                SYNTAX      Integer32
                MAX-ACCESS  read-only
                STATUS      current
                DESCRIPTION "PF2 Power Factor (1/1000)"
                ::= { minAveragesEntry 75042 }
minAvgPowerFactorTypeSPF2   OBJECT-TYPE
                SYNTAX      Unsigned32
                MAX-ACCESS  read-only
                STATUS      current
                DESCRIPTION "sPF1 Power Factor Type (1=Leading ; 2=Lagging)"
                ::= { minAveragesEntry 75049 }
minAvgPowerFactorPF2Date   OBJECT-TYPE
                SYNTAX      Unsigned32
                MAX-ACCESS  read-only
                STATUS      current
                DESCRIPTION "PF2 Power Factor Date"
                ::= { minAveragesEntry 75043 }
minAvgPowerFactorPF3   OBJECT-TYPE
                SYNTAX      Integer32
                MAX-ACCESS  read-only
                STATUS      current
                DESCRIPTION "PF3 Power Factor (1/1000)"
                ::= { minAveragesEntry 75044 }
minAvgPowerFactorTypeSPF3   OBJECT-TYPE
                SYNTAX      Unsigned32
                MAX-ACCESS  read-only
                STATUS      current
                DESCRIPTION "sPF1 Power Factor Type (1=Leading ; 2=Lagging)"
                ::= { minAveragesEntry 75050 }
minAvgPowerFactorPF3Date   OBJECT-TYPE
                SYNTAX      Unsigned32
                MAX-ACCESS  read-only
                STATUS      current
                DESCRIPTION "PF3 Power Factor Date"
                ::= { minAveragesEntry 75045 }

-- *******************************************************************************
-- ********************* MEASUREMENT INSTANTANEOUS CURRENT THD TABLE *************
-- *******************************************************************************
instantaneousCurrentTHDTable       OBJECT-TYPE
                SYNTAX      SEQUENCE OF SeqInstantaneousCurrentTHDEnt
                MAX-ACCESS  not-accessible
                STATUS      current
                DESCRIPTION "Instantaneous Current THD metrology Table"
                ::= { productMetrology 81 }

instantaneousCurrentTHDEntry       OBJECT-TYPE
                SYNTAX      SeqInstantaneousCurrentTHDEnt
                MAX-ACCESS  not-accessible
                STATUS      current
                DESCRIPTION "Instantaneous Current THD Data Table for given Product Index and Load Index"
                INDEX  { instCurrentTHDModbusAddress, instCurrentTHDLoadIndex  }
                ::= { instantaneousCurrentTHDTable 1 }

instCurrentTHDModbusAddress    OBJECT-TYPE
                SYNTAX      Unsigned32(1..255)
                MAX-ACCESS  read-only
                STATUS      current
                DESCRIPTION "Modbus address of the product"
                ::= { instantaneousCurrentTHDEntry 1 }

instCurrentTHDProductIndex    OBJECT-TYPE
                SYNTAX      Unsigned32(1..33)  -- 32 Products + 1 Gateway
                MAX-ACCESS  read-only
                STATUS      current
                DESCRIPTION "Index of the Product to reach (1 = Gateway itself)"
                ::= { instantaneousCurrentTHDEntry 5 }

instCurrentTHDLoadIndex       OBJECT-TYPE
                SYNTAX      Unsigned32(1..16)  -- 6 Loads + 10 MultiFluids
                MAX-ACCESS  read-only
                STATUS      current
                DESCRIPTION "Index of the Load to reach"
                ::= { instantaneousCurrentTHDEntry 6 }

instCurrentTHDLoadRowStatus      OBJECT-TYPE
                SYNTAX       RowStatus
                MAX-ACCESS   read-create
                STATUS       current
                DESCRIPTION "The status of this conceptual row."
                ::= { instantaneousCurrentTHDEntry 10 }

-- *******************
-- ** Instant THD ****
-- *******************
instTHDI1       OBJECT-TYPE
                SYNTAX      Unsigned32
                MAX-ACCESS  read-only
                STATUS      current
                DESCRIPTION "Instantaneous total harmonic distortion THD I1 (1/100 %)"
                ::= { instantaneousCurrentTHDEntry 100006 } 
instTHDI2       OBJECT-TYPE
                SYNTAX      Unsigned32
                MAX-ACCESS  read-only
                STATUS      current
                DESCRIPTION "Instantaneous total harmonic distortion THD I2 (1/100 %)"
                ::= { instantaneousCurrentTHDEntry 100007 } 
instTHDI3       OBJECT-TYPE
                SYNTAX      Unsigned32
                MAX-ACCESS  read-only
                STATUS      current
                DESCRIPTION "Instantaneous total harmonic distortion THD I3 (1/100 %)"
                ::= { instantaneousCurrentTHDEntry 100008 } 
instTHDIn       OBJECT-TYPE
                SYNTAX      Unsigned32
                MAX-ACCESS  read-only
                STATUS      current
                DESCRIPTION "Instantaneous total harmonic distortion THD In (1/100 %)"
                ::= { instantaneousCurrentTHDEntry 100009 } 

-- *******************
-- ** Maximum THD ****
-- *******************
instMaxTHDI1   OBJECT-TYPE
                SYNTAX      Unsigned32
                MAX-ACCESS  read-only
                STATUS      current
                DESCRIPTION "Maximum total harmonic distortion THD I1 (1/100 %)"
                ::= { instantaneousCurrentTHDEntry 100010 } 
instMaxTHDI1Date   OBJECT-TYPE
                SYNTAX      Unsigned32
                MAX-ACCESS  read-only
                STATUS      current
                DESCRIPTION "Date of Maximum total harmonic distortion THD I1"
                ::= { instantaneousCurrentTHDEntry 100011 }
instMaxTHDI2   OBJECT-TYPE
                SYNTAX      Unsigned32
                MAX-ACCESS  read-only
                STATUS      current
                DESCRIPTION "Maximum total harmonic distortion THD I2 (1/100 %)"
                ::= { instantaneousCurrentTHDEntry 100012 } 
instMaxTHDI2Date   OBJECT-TYPE
                SYNTAX      Unsigned32
                MAX-ACCESS  read-only
                STATUS      current
                DESCRIPTION "Date of Maximum total harmonic distortion THD I2"
                ::= { instantaneousCurrentTHDEntry 100013 } 
instMaxTHDI3   OBJECT-TYPE
                SYNTAX      Unsigned32
                MAX-ACCESS  read-only
                STATUS      current
                DESCRIPTION "Maximum total harmonic distortion THD I3 (1/100 %)"
                ::= { instantaneousCurrentTHDEntry 100014 } 
instMaxTHDI3Date   OBJECT-TYPE
                SYNTAX      Unsigned32
                MAX-ACCESS  read-only
                STATUS      current
                DESCRIPTION "Date of Maximum total harmonic distortion THD I3"
                ::= { instantaneousCurrentTHDEntry 100015 } 
instMaxTHDIn   OBJECT-TYPE
                SYNTAX      Unsigned32
                MAX-ACCESS  read-only
                STATUS      current
                DESCRIPTION "Maximum total harmonic distortion THD In (1/100 %)"
                ::= { instantaneousCurrentTHDEntry 100016 } 
instMaxTHDInDate   OBJECT-TYPE
                SYNTAX      Unsigned32
                MAX-ACCESS  read-only
                STATUS      current
                DESCRIPTION "Date of Maximum total harmonic distortion THD In"
                ::= { instantaneousCurrentTHDEntry 100017 }  

-- *******************
-- ** Minimum THD ****
-- *******************
instMinTHDI1   OBJECT-TYPE
                SYNTAX      Unsigned32
                MAX-ACCESS  read-only
                STATUS      current
                DESCRIPTION "Minimum total harmonic distortion THD I1 (1/100 %)"
                ::= { instantaneousCurrentTHDEntry 100018 } 
instMinTHDI1Date   OBJECT-TYPE
                SYNTAX      Unsigned32
                MAX-ACCESS  read-only
                STATUS      current
                DESCRIPTION "Date of Minimum total harmonic distortion THD I1"
                ::= { instantaneousCurrentTHDEntry 100019 }
instMinTHDI2   OBJECT-TYPE
                SYNTAX      Unsigned32
                MAX-ACCESS  read-only
                STATUS      current
                DESCRIPTION "Minimum total harmonic distortion THD I2 (1/100 %)"
                ::= { instantaneousCurrentTHDEntry 100020 } 
instMinTHDI2Date   OBJECT-TYPE
                SYNTAX      Unsigned32
                MAX-ACCESS  read-only
                STATUS      current
                DESCRIPTION "Date of Minimum total harmonic distortion THD I2"
                ::= { instantaneousCurrentTHDEntry 100021 } 
instMinTHDI3   OBJECT-TYPE
                SYNTAX      Unsigned32
                MAX-ACCESS  read-only
                STATUS      current
                DESCRIPTION "Minimum total harmonic distortion THD I3 (1/100 %)"
                ::= { instantaneousCurrentTHDEntry 100022 } 
instMinTHDI3Date   OBJECT-TYPE
                SYNTAX      Unsigned32
                MAX-ACCESS  read-only
                STATUS      current
                DESCRIPTION "Date of Minimum total harmonic distortion THD I3"
                ::= { instantaneousCurrentTHDEntry 100023 } 
instMinTHDIn   OBJECT-TYPE
                SYNTAX      Unsigned32
                MAX-ACCESS  read-only
                STATUS      current
                DESCRIPTION "Minimum total harmonic distortion THD In (1/100 %)"
                ::= { instantaneousCurrentTHDEntry 100024 } 
instMinTHDInDate   OBJECT-TYPE
                SYNTAX      Unsigned32
                MAX-ACCESS  read-only
                STATUS      current
                DESCRIPTION "Date of Minimum total harmonic distortion THD In"
                ::= { instantaneousCurrentTHDEntry 100025 }


-- *******************************************************************************
-- ********************* MEASUREMENT INSTANTANEOUS VOLTAGE THD TABLE *************
-- *******************************************************************************
instantaneousVoltageTHDTable       OBJECT-TYPE
                SYNTAX      SEQUENCE OF SeqInstantaneousVoltageTHDEnt
                MAX-ACCESS  not-accessible
                STATUS      current
                DESCRIPTION "Instantaneous Voltage THD metrology Table"
                ::= { productMetrology 82 }

instantaneousVoltageTHDEntry       OBJECT-TYPE
                SYNTAX      SeqInstantaneousVoltageTHDEnt
                MAX-ACCESS  not-accessible
                STATUS      current
                DESCRIPTION "Instantaneous Voltage THD Data Table for given Product Index"
                INDEX  { instVoltageTHDModbusAddress }
                ::= { instantaneousVoltageTHDTable 1 }

instVoltageTHDModbusAddress    OBJECT-TYPE
                SYNTAX      Unsigned32(1..255)
                MAX-ACCESS  read-only
                STATUS      current
                DESCRIPTION "Modbus address of the product"
                ::= { instantaneousVoltageTHDEntry 1 }

instVoltageTHDProductIndex    OBJECT-TYPE
                SYNTAX      Unsigned32(1..33)  -- 32 Products + 1 Gateway
                MAX-ACCESS  read-only
                STATUS      current
                DESCRIPTION "Index of the Product to reach (1 = Gateway itself)"
                ::= { instantaneousVoltageTHDEntry 5 }

instVoltageTHDLoadRowStatus      OBJECT-TYPE
                SYNTAX       RowStatus
                MAX-ACCESS   read-create
                STATUS       current
                DESCRIPTION "The status of this conceptual row."
                ::= { instantaneousVoltageTHDEntry 10 }

-- *******************
-- ** Instant THD ****
-- *******************
instTHDV1       OBJECT-TYPE
                SYNTAX      Unsigned32
                MAX-ACCESS  read-only
                STATUS      current
                DESCRIPTION "Instantaneous total harmonic distortion THD V1 (1/100 %)"
                ::= { instantaneousVoltageTHDEntry 100000 } 
instTHDV2       OBJECT-TYPE
                SYNTAX      Unsigned32
                MAX-ACCESS  read-only
                STATUS      current
                DESCRIPTION "Instantaneous total harmonic distortion THD V2 (1/100 %)"
                ::= { instantaneousVoltageTHDEntry 100001 } 
instTHDV3       OBJECT-TYPE
                SYNTAX      Unsigned32
                MAX-ACCESS  read-only
                STATUS      current
                DESCRIPTION "Instantaneous total harmonic distortion THD V3 (1/100 %)"
                ::= { instantaneousVoltageTHDEntry 100002 }
instTHDU12      OBJECT-TYPE
                SYNTAX      Unsigned32
                MAX-ACCESS  read-only
                STATUS      current
                DESCRIPTION "Instantaneous total harmonic distortion THD U12 (1/100 %)"
                ::= { instantaneousVoltageTHDEntry 100003 } 
instTHDU23      OBJECT-TYPE
                SYNTAX      Unsigned32
                MAX-ACCESS  read-only
                STATUS      current
                DESCRIPTION "Instantaneous total harmonic distortion THD U23 (1/100 %)"
                ::= { instantaneousVoltageTHDEntry 100004 } 
instTHDU31      OBJECT-TYPE
                SYNTAX      Unsigned32
                MAX-ACCESS  read-only
                STATUS      current
                DESCRIPTION "Instantaneous total harmonic distortion THD U31 (1/100 %)"
                ::= { instantaneousVoltageTHDEntry 100005 } 

-- *******************
-- ** Maximum THD ****
-- *******************
instMaxTHDV1   OBJECT-TYPE
                SYNTAX      Unsigned32
                MAX-ACCESS  read-only
                STATUS      current
                DESCRIPTION "Maximum total harmonic distortion THD V1 (1/100 %)"
                ::= { instantaneousVoltageTHDEntry 100032 } 
instMaxTHDV1Date   OBJECT-TYPE
                SYNTAX      Unsigned32
                MAX-ACCESS  read-only
                STATUS      current
                DESCRIPTION "Date of Maximum total harmonic distortion THD V1"
                ::= { instantaneousVoltageTHDEntry 100033 }
instMaxTHDV2   OBJECT-TYPE
                SYNTAX      Unsigned32
                MAX-ACCESS  read-only
                STATUS      current
                DESCRIPTION "Maximum total harmonic distortion THD V2 (1/100 %)"
                ::= { instantaneousVoltageTHDEntry 100034 } 
instMaxTHDV2Date   OBJECT-TYPE
                SYNTAX      Unsigned32
                MAX-ACCESS  read-only
                STATUS      current
                DESCRIPTION "Date of Maximum total harmonic distortion THD V2"
                ::= { instantaneousVoltageTHDEntry 100035 } 
instMaxTHDV3   OBJECT-TYPE
                SYNTAX      Unsigned32
                MAX-ACCESS  read-only
                STATUS      current
                DESCRIPTION "Maximum total harmonic distortion THD V3 (1/100 %)"
                ::= { instantaneousVoltageTHDEntry 100036 } 
instMaxTHDV3Date   OBJECT-TYPE
                SYNTAX      Unsigned32
                MAX-ACCESS  read-only
                STATUS      current
                DESCRIPTION "Date of Maximum total harmonic distortion THD V3"
                ::= { instantaneousVoltageTHDEntry 100037 } 
instMaxTHDU12   OBJECT-TYPE
                SYNTAX      Unsigned32
                MAX-ACCESS  read-only
                STATUS      current
                DESCRIPTION "Maximum total harmonic distortion THD U12 (1/100 %)"
                ::= { instantaneousVoltageTHDEntry 100038 } 
instMaxTHDU12Date   OBJECT-TYPE
                SYNTAX      Unsigned32
                MAX-ACCESS  read-only
                STATUS      current
                DESCRIPTION "Date of Maximum total harmonic distortion THD U12"
                ::= { instantaneousVoltageTHDEntry 100039 }
instMaxTHDU23   OBJECT-TYPE
                SYNTAX      Unsigned32
                MAX-ACCESS  read-only
                STATUS      current
                DESCRIPTION "Maximum total harmonic distortion THD U23 (1/100 %)"
                ::= { instantaneousVoltageTHDEntry 100040 } 
instMaxTHDU23Date   OBJECT-TYPE
                SYNTAX      Unsigned32
                MAX-ACCESS  read-only
                STATUS      current
                DESCRIPTION "Date of Maximum total harmonic distortion THD U23"
                ::= { instantaneousVoltageTHDEntry 100041 } 
instMaxTHDU31   OBJECT-TYPE
                SYNTAX      Unsigned32
                MAX-ACCESS  read-only
                STATUS      current
                DESCRIPTION "Maximum total harmonic distortion THD U31 (1/100 %)"
                ::= { instantaneousVoltageTHDEntry 100042 } 
instMaxTHDU31Date   OBJECT-TYPE
                SYNTAX      Unsigned32
                MAX-ACCESS  read-only
                STATUS      current
                DESCRIPTION "Date of Maximum total harmonic distortion THD U31"
                ::= { instantaneousVoltageTHDEntry 100043 } 

-- *******************
-- ** Minimum THD ****
-- *******************
instMinTHDV1   OBJECT-TYPE
                SYNTAX      Unsigned32
                MAX-ACCESS  read-only
                STATUS      current
                DESCRIPTION "Minimum total harmonic distortion THD V1 (1/100 %)"
                ::= { instantaneousVoltageTHDEntry 100044 } 
instMinTHDV1Date   OBJECT-TYPE
                SYNTAX      Unsigned32
                MAX-ACCESS  read-only
                STATUS      current
                DESCRIPTION "Date of Minimum total harmonic distortion THD V1"
                ::= { instantaneousVoltageTHDEntry 100045 }
instMinTHDV2   OBJECT-TYPE
                SYNTAX      Unsigned32
                MAX-ACCESS  read-only
                STATUS      current
                DESCRIPTION "Minimum total harmonic distortion THD V2 (1/100 %)"
                ::= { instantaneousVoltageTHDEntry 100046 } 
instMinTHDV2Date   OBJECT-TYPE
                SYNTAX      Unsigned32
                MAX-ACCESS  read-only
                STATUS      current
                DESCRIPTION "Date of Minimum total harmonic distortion THD V2"
                ::= { instantaneousVoltageTHDEntry 100047 } 
instMinTHDV3   OBJECT-TYPE
                SYNTAX      Unsigned32
                MAX-ACCESS  read-only
                STATUS      current
                DESCRIPTION "Minimum total harmonic distortion THD V3 (1/100 %)"
                ::= { instantaneousVoltageTHDEntry 100048 } 
instMinTHDV3Date   OBJECT-TYPE
                SYNTAX      Unsigned32
                MAX-ACCESS  read-only
                STATUS      current
                DESCRIPTION "Date of Minimum total harmonic distortion THD V3"
                ::= { instantaneousVoltageTHDEntry 100049 } 
instMinTHDU12   OBJECT-TYPE
                SYNTAX      Unsigned32
                MAX-ACCESS  read-only
                STATUS      current
                DESCRIPTION "Minimum total harmonic distortion THD U12 (1/100 %)"
                ::= { instantaneousVoltageTHDEntry 100050 } 
instMinTHDU12Date   OBJECT-TYPE
                SYNTAX      Unsigned32
                MAX-ACCESS  read-only
                STATUS      current
                DESCRIPTION "Date of Minimum total harmonic distortion THD U12"
                ::= { instantaneousVoltageTHDEntry 100051 }
instMinTHDU23   OBJECT-TYPE
                SYNTAX      Unsigned32
                MAX-ACCESS  read-only
                STATUS      current
                DESCRIPTION "Minimum total harmonic distortion THD U23 (1/100 %)"
                ::= { instantaneousVoltageTHDEntry 100052 } 
instMinTHDU23Date   OBJECT-TYPE
                SYNTAX      Unsigned32
                MAX-ACCESS  read-only
                STATUS      current
                DESCRIPTION "Date of Minimum total harmonic distortion THD U23"
                ::= { instantaneousVoltageTHDEntry 100053 } 
instMinTHDU31   OBJECT-TYPE
                SYNTAX      Unsigned32
                MAX-ACCESS  read-only
                STATUS      current
                DESCRIPTION "Minimum total harmonic distortion THD U31 (1/100 %)"
                ::= { instantaneousVoltageTHDEntry 100054 } 
instMinTHDU31Date   OBJECT-TYPE
                SYNTAX      Unsigned32
                MAX-ACCESS  read-only
                STATUS      current
                DESCRIPTION "Date of Minimum total harmonic distortion THD U31"
                ::= { instantaneousVoltageTHDEntry 100055 } 


-- *******************************************************************************
-- ********************* MEASUREMENT INSTANTANEOUS CURRENT HARMONICS TABLE *******
-- *******************************************************************************
instantaneousCurrentHarmonicsTable       OBJECT-TYPE
                SYNTAX      SEQUENCE OF SeqInstantaneousCurrentHarmonicsEnt
                MAX-ACCESS  not-accessible
                STATUS      current
                DESCRIPTION "Instantaneous Current Harmonics metrology Table"
                ::= { productMetrology 83 }

instantaneousCurrentHarmonicsEntry       OBJECT-TYPE
                SYNTAX      SeqInstantaneousCurrentHarmonicsEnt
                MAX-ACCESS  not-accessible
                STATUS      current
                DESCRIPTION "Instantaneous Harmonics Data Table for given Product Index and Load Index"
                INDEX  { instCurrentHarmonicsModbusAddress, instCurrentHarmonicsLoadIndex  }
                ::= { instantaneousCurrentHarmonicsTable 1 }

instCurrentHarmonicsModbusAddress    OBJECT-TYPE
                SYNTAX      Unsigned32(1..255)
                MAX-ACCESS  read-only
                STATUS      current
                DESCRIPTION "Modbus address of the product"
                ::= { instantaneousCurrentHarmonicsEntry 1 }

instCurrentHarmonicsProductIndex    OBJECT-TYPE
                SYNTAX      Unsigned32(1..33)  -- 32 Products + 1 Gateway
                MAX-ACCESS  read-only
                STATUS      current
                DESCRIPTION "Index of the Product to reach (1 = Gateway itself)"
                ::= { instantaneousCurrentHarmonicsEntry 5 }

instCurrentHarmonicsLoadIndex       OBJECT-TYPE
                SYNTAX      Unsigned32(1..16)  -- 6 Loads + 10 MultiFluids
                MAX-ACCESS  read-only
                STATUS      current
                DESCRIPTION "Index of the Load to reach"
                ::= { instantaneousCurrentHarmonicsEntry 6 }

instCurrentHarmonicsLoadRowStatus      OBJECT-TYPE
                SYNTAX       RowStatus
                MAX-ACCESS   read-create
                STATUS       current
                DESCRIPTION "The status of this conceptual row."
                ::= { instantaneousCurrentHarmonicsEntry 10 }

-- *******************
-- ** I1 Harmonics ***
-- *******************
instHarmonicsRow02I1   OBJECT-TYPE
                SYNTAX      Unsigned32
                MAX-ACCESS  read-only
                STATUS      current
                DESCRIPTION "Current Harmonic Row 2 of I1 (1/100 %)"
                ::= { instantaneousCurrentHarmonicsEntry 50172 } 
                
instHarmonicsRow03I1   OBJECT-TYPE
                SYNTAX      Unsigned32
                MAX-ACCESS  read-only
                STATUS      current
                DESCRIPTION "Current Harmonic Row 3 of I1 (1/100 %)"
                ::= { instantaneousCurrentHarmonicsEntry 50173 } 

instHarmonicsRow04I1   OBJECT-TYPE
                SYNTAX      Unsigned32
                MAX-ACCESS  read-only
                STATUS      current
                DESCRIPTION "Current Harmonic Row 4 of I1 (1/100 %)"
                ::= { instantaneousCurrentHarmonicsEntry 50174 } 

instHarmonicsRow05I1   OBJECT-TYPE
                SYNTAX      Unsigned32
                MAX-ACCESS  read-only
                STATUS      current
                DESCRIPTION "Current Harmonic Row 5 of I1 (1/100 %)"
                ::= { instantaneousCurrentHarmonicsEntry 50175 } 

instHarmonicsRow06I1   OBJECT-TYPE
                SYNTAX      Unsigned32
                MAX-ACCESS  read-only
                STATUS      current
                DESCRIPTION "Current Harmonic Row 6 of I1 (1/100 %)"
                ::= { instantaneousCurrentHarmonicsEntry 50176 } 
                
instHarmonicsRow07I1   OBJECT-TYPE
                SYNTAX      Unsigned32
                MAX-ACCESS  read-only
                STATUS      current
                DESCRIPTION "Current Harmonic Row 7 of I1 (1/100 %)"
                ::= { instantaneousCurrentHarmonicsEntry 50177 } 

instHarmonicsRow08I1   OBJECT-TYPE
                SYNTAX      Unsigned32
                MAX-ACCESS  read-only
                STATUS      current
                DESCRIPTION "Current Harmonic Row 8 of I1 (1/100 %)"
                ::= { instantaneousCurrentHarmonicsEntry 50178 } 

instHarmonicsRow09I1   OBJECT-TYPE
                SYNTAX      Unsigned32
                MAX-ACCESS  read-only
                STATUS      current
                DESCRIPTION "Current Harmonic Row 9 of I1 (1/100 %)"
                ::= { instantaneousCurrentHarmonicsEntry 50179 } 

instHarmonicsRow10I1   OBJECT-TYPE
                SYNTAX      Unsigned32
                MAX-ACCESS  read-only
                STATUS      current
                DESCRIPTION "Current Harmonic Row 10 of I1 (1/100 %)"
                ::= { instantaneousCurrentHarmonicsEntry 50180 } 

-- *******************
-- ** I2 Harmonics ***
-- *******************
instHarmonicsRow02I2   OBJECT-TYPE
                SYNTAX      Unsigned32
                MAX-ACCESS  read-only
                STATUS      current
                DESCRIPTION "Current Harmonic Row 2 of I2 (1/100 %)"
                ::= { instantaneousCurrentHarmonicsEntry 50199 } 
                
instHarmonicsRow03I2   OBJECT-TYPE
                SYNTAX      Unsigned32
                MAX-ACCESS  read-only
                STATUS      current
                DESCRIPTION "Current Harmonic Row 3 of I2 (1/100 %)"
                ::= { instantaneousCurrentHarmonicsEntry 50200 } 

instHarmonicsRow04I2   OBJECT-TYPE
                SYNTAX      Unsigned32
                MAX-ACCESS  read-only
                STATUS      current
                DESCRIPTION "Current Harmonic Row 4 of I2 (1/100 %)"
                ::= { instantaneousCurrentHarmonicsEntry 50201 } 

instHarmonicsRow05I2   OBJECT-TYPE
                SYNTAX      Unsigned32
                MAX-ACCESS  read-only
                STATUS      current
                DESCRIPTION "Current Harmonic Row 5 of I2 (1/100 %)"
                ::= { instantaneousCurrentHarmonicsEntry 50202 } 

instHarmonicsRow06I2   OBJECT-TYPE
                SYNTAX      Unsigned32
                MAX-ACCESS  read-only
                STATUS      current
                DESCRIPTION "Current Harmonic Row 6 of I2 (1/100 %)"
                ::= { instantaneousCurrentHarmonicsEntry 50203 } 
                
instHarmonicsRow07I2   OBJECT-TYPE
                SYNTAX      Unsigned32
                MAX-ACCESS  read-only
                STATUS      current
                DESCRIPTION "Current Harmonic Row 7 of I2 (1/100 %)"
                ::= { instantaneousCurrentHarmonicsEntry 50204 } 

instHarmonicsRow08I2   OBJECT-TYPE
                SYNTAX      Unsigned32
                MAX-ACCESS  read-only
                STATUS      current
                DESCRIPTION "Current Harmonic Row 8 of I2 (1/100 %)"
                ::= { instantaneousCurrentHarmonicsEntry 50205 } 

instHarmonicsRow09I2   OBJECT-TYPE
                SYNTAX      Unsigned32
                MAX-ACCESS  read-only
                STATUS      current
                DESCRIPTION "Current Harmonic Row 9 of I2 (1/100 %)"
                ::= { instantaneousCurrentHarmonicsEntry 50206 } 

instHarmonicsRow10I2   OBJECT-TYPE
                SYNTAX      Unsigned32
                MAX-ACCESS  read-only
                STATUS      current
                DESCRIPTION "Current Harmonic Row 10 of I2 (1/100 %)"
                ::= { instantaneousCurrentHarmonicsEntry 50207 } 

-- *******************
-- ** I3 Harmonics ***
-- *******************
instHarmonicsRow02I3   OBJECT-TYPE
                SYNTAX      Unsigned32
                MAX-ACCESS  read-only
                STATUS      current
                DESCRIPTION "Current Harmonic Row 2 of I3 (1/100 %)"
                ::= { instantaneousCurrentHarmonicsEntry 50226 } 
                
instHarmonicsRow03I3   OBJECT-TYPE
                SYNTAX      Unsigned32
                MAX-ACCESS  read-only
                STATUS      current
                DESCRIPTION "Current Harmonic Row 3 of I3 (1/100 %)"
                ::= { instantaneousCurrentHarmonicsEntry 50227 } 

instHarmonicsRow04I3   OBJECT-TYPE
                SYNTAX      Unsigned32
                MAX-ACCESS  read-only
                STATUS      current
                DESCRIPTION "Current Harmonic Row 4 of I3 (1/100 %)"
                ::= { instantaneousCurrentHarmonicsEntry 50228 } 

instHarmonicsRow05I3   OBJECT-TYPE
                SYNTAX      Unsigned32
                MAX-ACCESS  read-only
                STATUS      current
                DESCRIPTION "Current Harmonic Row 5 of I3 (1/100 %)"
                ::= { instantaneousCurrentHarmonicsEntry 50229 } 

instHarmonicsRow06I3   OBJECT-TYPE
                SYNTAX      Unsigned32
                MAX-ACCESS  read-only
                STATUS      current
                DESCRIPTION "Current Harmonic Row 6 of I3 (1/100 %)"
                ::= { instantaneousCurrentHarmonicsEntry 50230 } 
                
instHarmonicsRow07I3   OBJECT-TYPE
                SYNTAX      Unsigned32
                MAX-ACCESS  read-only
                STATUS      current
                DESCRIPTION "Current Harmonic Row 7 of I3 (1/100 %)"
                ::= { instantaneousCurrentHarmonicsEntry 50231 } 

instHarmonicsRow08I3   OBJECT-TYPE
                SYNTAX      Unsigned32
                MAX-ACCESS  read-only
                STATUS      current
                DESCRIPTION "Current Harmonic Row 8 of I3 (1/100 %)"
                ::= { instantaneousCurrentHarmonicsEntry 50232 } 

instHarmonicsRow09I3   OBJECT-TYPE
                SYNTAX      Unsigned32
                MAX-ACCESS  read-only
                STATUS      current
                DESCRIPTION "Current Harmonic Row 9 of I3 (1/100 %)"
                ::= { instantaneousCurrentHarmonicsEntry 50233 } 

instHarmonicsRow10I3   OBJECT-TYPE
                SYNTAX      Unsigned32
                MAX-ACCESS  read-only
                STATUS      current
                DESCRIPTION "Current Harmonic Row 10 of I3 (1/100 %)"
                ::= { instantaneousCurrentHarmonicsEntry 50234 }

-- *******************
-- ** In Harmonics ***
-- *******************
instHarmonicsRow02In   OBJECT-TYPE
                SYNTAX      Unsigned32
                MAX-ACCESS  read-only
                STATUS      current
                DESCRIPTION "Current Harmonic Row 2 of In (1/100 %)"
                ::= { instantaneousCurrentHarmonicsEntry 50253 } 
                
instHarmonicsRow03In   OBJECT-TYPE
                SYNTAX      Unsigned32
                MAX-ACCESS  read-only
                STATUS      current
                DESCRIPTION "Current Harmonic Row 3 of In (1/100 %)"
                ::= { instantaneousCurrentHarmonicsEntry 50254 } 

instHarmonicsRow04In   OBJECT-TYPE
                SYNTAX      Unsigned32
                MAX-ACCESS  read-only
                STATUS      current
                DESCRIPTION "Current Harmonic Row 4 of In (1/100 %)"
                ::= { instantaneousCurrentHarmonicsEntry 50255 } 

instHarmonicsRow05In   OBJECT-TYPE
                SYNTAX      Unsigned32
                MAX-ACCESS  read-only
                STATUS      current
                DESCRIPTION "Current Harmonic Row 5 of In (1/100 %)"
                ::= { instantaneousCurrentHarmonicsEntry 50256 } 

instHarmonicsRow06In   OBJECT-TYPE
                SYNTAX      Unsigned32
                MAX-ACCESS  read-only
                STATUS      current
                DESCRIPTION "Current Harmonic Row 6 of In (1/100 %)"
                ::= { instantaneousCurrentHarmonicsEntry 50257 } 
                
instHarmonicsRow07In   OBJECT-TYPE
                SYNTAX      Unsigned32
                MAX-ACCESS  read-only
                STATUS      current
                DESCRIPTION "Current Harmonic Row 7 of In (1/100 %)"
                ::= { instantaneousCurrentHarmonicsEntry 50258 } 

instHarmonicsRow08In   OBJECT-TYPE
                SYNTAX      Unsigned32
                MAX-ACCESS  read-only
                STATUS      current
                DESCRIPTION "Current Harmonic Row 8 of In (1/100 %)"
                ::= { instantaneousCurrentHarmonicsEntry 50259 } 

instHarmonicsRow09In   OBJECT-TYPE
                SYNTAX      Unsigned32
                MAX-ACCESS  read-only
                STATUS      current
                DESCRIPTION "Current Harmonic Row 9 of In (1/100 %)"
                ::= { instantaneousCurrentHarmonicsEntry 50260 } 

instHarmonicsRow10In   OBJECT-TYPE
                SYNTAX      Unsigned32
                MAX-ACCESS  read-only
                STATUS      current
                DESCRIPTION "Current Harmonic Row 10 of In (1/100 %)"
                ::= { instantaneousCurrentHarmonicsEntry 50261 }


-- *******************************************************************************
-- ********************* MEASUREMENT INSTANTANEOUS VOLTAGE PH-N HARMONICS TABLE **
-- *******************************************************************************
instantaneousVoltagePhNHarmonicsTable       OBJECT-TYPE
                SYNTAX      SEQUENCE OF SeqInstantaneousVoltagePhNHarmonicsEnt
                MAX-ACCESS  not-accessible
                STATUS      current
                DESCRIPTION "Instantaneous Voltage Phase-Neutral Harmonics metrology Table"
                ::= { productMetrology 84 }

instantaneousVoltagePhNHarmonicsEntry       OBJECT-TYPE
                SYNTAX      SeqInstantaneousVoltagePhNHarmonicsEnt
                MAX-ACCESS  not-accessible
                STATUS      current
                DESCRIPTION "Instantaneous Harmonics Data Table for given Product Index and Load Index"
                INDEX  { instVoltagePhNHarmonicsModbusAddress }
                ::= { instantaneousVoltagePhNHarmonicsTable 1 }

instVoltagePhNHarmonicsModbusAddress    OBJECT-TYPE
                SYNTAX      Unsigned32(1..255)
                MAX-ACCESS  read-only
                STATUS      current
                DESCRIPTION "Modbus address of the product"
                ::= { instantaneousVoltagePhNHarmonicsEntry 1 }

instVoltagePhNHarmonicsProductIndex    OBJECT-TYPE
                SYNTAX      Unsigned32(1..33)  -- 32 Products + 1 Gateway
                MAX-ACCESS  read-only
                STATUS      current
                DESCRIPTION "Index of the Product to reach (1 = Gateway itself)"
                ::= { instantaneousVoltagePhNHarmonicsEntry 5 }

instVoltagePhNHarmonicsLoadRowStatus      OBJECT-TYPE
                SYNTAX       RowStatus
                MAX-ACCESS   read-create
                STATUS       current
                DESCRIPTION "The status of this conceptual row."
                ::= { instantaneousVoltagePhNHarmonicsEntry 10 }

-- *******************
-- ** V1 Harmonics ***
-- *******************
instHarmonicsRow02V1   OBJECT-TYPE
                SYNTAX      Unsigned32
                MAX-ACCESS  read-only
                STATUS      current
                DESCRIPTION "Voltage Ph-N Harmonic Row 2 of V1 (1/100 %)"
                ::= { instantaneousVoltagePhNHarmonicsEntry 50010 } 
                
instHarmonicsRow03V1   OBJECT-TYPE
                SYNTAX      Unsigned32
                MAX-ACCESS  read-only
                STATUS      current
                DESCRIPTION "Voltage Ph-N Harmonic Row 3 of V1 (1/100 %)"
                ::= { instantaneousVoltagePhNHarmonicsEntry 50011 } 

instHarmonicsRow04V1   OBJECT-TYPE
                SYNTAX      Unsigned32
                MAX-ACCESS  read-only
                STATUS      current
                DESCRIPTION "Voltage Ph-N Harmonic Row 4 of V1 (1/100 %)"
                ::= { instantaneousVoltagePhNHarmonicsEntry 50012 } 

instHarmonicsRow05V1   OBJECT-TYPE
                SYNTAX      Unsigned32
                MAX-ACCESS  read-only
                STATUS      current
                DESCRIPTION "Voltage Ph-N Harmonic Row 5 of V1 (1/100 %)"
                ::= { instantaneousVoltagePhNHarmonicsEntry 50013 } 

instHarmonicsRow06V1   OBJECT-TYPE
                SYNTAX      Unsigned32
                MAX-ACCESS  read-only
                STATUS      current
                DESCRIPTION "Voltage Ph-N Harmonic Row 6 of V1 (1/100 %)"
                ::= { instantaneousVoltagePhNHarmonicsEntry 50014 } 
                
instHarmonicsRow07V1   OBJECT-TYPE
                SYNTAX      Unsigned32
                MAX-ACCESS  read-only
                STATUS      current
                DESCRIPTION "Voltage Ph-N Harmonic Row 7 of V1 (1/100 %)"
                ::= { instantaneousVoltagePhNHarmonicsEntry 50015 } 

instHarmonicsRow08V1   OBJECT-TYPE
                SYNTAX      Unsigned32
                MAX-ACCESS  read-only
                STATUS      current
                DESCRIPTION "Voltage Ph-N Harmonic Row 8 of V1 (1/100 %)"
                ::= { instantaneousVoltagePhNHarmonicsEntry 50016 } 

instHarmonicsRow09V1   OBJECT-TYPE
                SYNTAX      Unsigned32
                MAX-ACCESS  read-only
                STATUS      current
                DESCRIPTION "Voltage Ph-N Harmonic Row 9 of V1 (1/100 %)"
                ::= { instantaneousVoltagePhNHarmonicsEntry 50017 } 

instHarmonicsRow10V1   OBJECT-TYPE
                SYNTAX      Unsigned32
                MAX-ACCESS  read-only
                STATUS      current
                DESCRIPTION "Voltage Ph-N Harmonic Row 10 of V1 (1/100 %)"
                ::= { instantaneousVoltagePhNHarmonicsEntry 50018 } 

-- *******************
-- ** V2 Harmonics ***
-- *******************
instHarmonicsRow02V2   OBJECT-TYPE
                SYNTAX      Unsigned32
                MAX-ACCESS  read-only
                STATUS      current
                DESCRIPTION "Voltage Ph-N Harmonic Row 2 of V2 (1/100 %)"
                ::= { instantaneousVoltagePhNHarmonicsEntry 50037 } 
                
instHarmonicsRow03V2   OBJECT-TYPE
                SYNTAX      Unsigned32
                MAX-ACCESS  read-only
                STATUS      current
                DESCRIPTION "Voltage Ph-N Harmonic Row 3 of V2 (1/100 %)"
                ::= { instantaneousVoltagePhNHarmonicsEntry 50038 } 

instHarmonicsRow04V2   OBJECT-TYPE
                SYNTAX      Unsigned32
                MAX-ACCESS  read-only
                STATUS      current
                DESCRIPTION "Voltage Ph-N Harmonic Row 4 of V2 (1/100 %)"
                ::= { instantaneousVoltagePhNHarmonicsEntry 50039 } 

instHarmonicsRow05V2   OBJECT-TYPE
                SYNTAX      Unsigned32
                MAX-ACCESS  read-only
                STATUS      current
                DESCRIPTION "Voltage Ph-N Harmonic Row 5 of V2 (1/100 %)"
                ::= { instantaneousVoltagePhNHarmonicsEntry 50040 } 

instHarmonicsRow06V2   OBJECT-TYPE
                SYNTAX      Unsigned32
                MAX-ACCESS  read-only
                STATUS      current
                DESCRIPTION "Voltage Ph-N Harmonic Row 6 of V2 (1/100 %)"
                ::= { instantaneousVoltagePhNHarmonicsEntry 50041 } 
                
instHarmonicsRow07V2   OBJECT-TYPE
                SYNTAX      Unsigned32
                MAX-ACCESS  read-only
                STATUS      current
                DESCRIPTION "Voltage Ph-N Harmonic Row 7 of V2 (1/100 %)"
                ::= { instantaneousVoltagePhNHarmonicsEntry 50042 } 

instHarmonicsRow08V2   OBJECT-TYPE
                SYNTAX      Unsigned32
                MAX-ACCESS  read-only
                STATUS      current
                DESCRIPTION "Voltage Ph-N Harmonic Row 8 of V2 (1/100 %)"
                ::= { instantaneousVoltagePhNHarmonicsEntry 50043 } 

instHarmonicsRow09V2   OBJECT-TYPE
                SYNTAX      Unsigned32
                MAX-ACCESS  read-only
                STATUS      current
                DESCRIPTION "Voltage Ph-N Harmonic Row 9 of V2 (1/100 %)"
                ::= { instantaneousVoltagePhNHarmonicsEntry 50044 } 

instHarmonicsRow10V2   OBJECT-TYPE
                SYNTAX      Unsigned32
                MAX-ACCESS  read-only
                STATUS      current
                DESCRIPTION "Voltage Ph-N Harmonic Row 10 of V2 (1/100 %)"
                ::= { instantaneousVoltagePhNHarmonicsEntry 50045 } 

-- *******************
-- ** V3 Harmonics ***
-- *******************
instHarmonicsRow02V3   OBJECT-TYPE
                SYNTAX      Unsigned32
                MAX-ACCESS  read-only
                STATUS      current
                DESCRIPTION "Voltage Ph-N Harmonic Row 2 of V3 (1/100 %)"
                ::= { instantaneousVoltagePhNHarmonicsEntry 50064 } 
                
instHarmonicsRow03V3   OBJECT-TYPE
                SYNTAX      Unsigned32
                MAX-ACCESS  read-only
                STATUS      current
                DESCRIPTION "Voltage Ph-N Harmonic Row 3 of V3 (1/100 %)"
                ::= { instantaneousVoltagePhNHarmonicsEntry 50065 } 

instHarmonicsRow04V3   OBJECT-TYPE
                SYNTAX      Unsigned32
                MAX-ACCESS  read-only
                STATUS      current
                DESCRIPTION "Voltage Ph-N Harmonic Row 4 of V3 (1/100 %)"
                ::= { instantaneousVoltagePhNHarmonicsEntry 50066 } 

instHarmonicsRow05V3   OBJECT-TYPE
                SYNTAX      Unsigned32
                MAX-ACCESS  read-only
                STATUS      current
                DESCRIPTION "Voltage Ph-N Harmonic Row 5 of V3 (1/100 %)"
                ::= { instantaneousVoltagePhNHarmonicsEntry 50067 } 

instHarmonicsRow06V3   OBJECT-TYPE
                SYNTAX      Unsigned32
                MAX-ACCESS  read-only
                STATUS      current
                DESCRIPTION "Voltage Ph-N Harmonic Row 6 of V3 (1/100 %)"
                ::= { instantaneousVoltagePhNHarmonicsEntry 50068 } 
                
instHarmonicsRow07V3   OBJECT-TYPE
                SYNTAX      Unsigned32
                MAX-ACCESS  read-only
                STATUS      current
                DESCRIPTION "Voltage Ph-N Harmonic Row 7 of V3 (1/100 %)"
                ::= { instantaneousVoltagePhNHarmonicsEntry 50069 } 

instHarmonicsRow08V3   OBJECT-TYPE
                SYNTAX      Unsigned32
                MAX-ACCESS  read-only
                STATUS      current
                DESCRIPTION "Voltage Ph-N Harmonic Row 8 of V3 (1/100 %)"
                ::= { instantaneousVoltagePhNHarmonicsEntry 50070 } 

instHarmonicsRow09V3   OBJECT-TYPE
                SYNTAX      Unsigned32
                MAX-ACCESS  read-only
                STATUS      current
                DESCRIPTION "Voltage Ph-N Harmonic Row 9 of V3 (1/100 %)"
                ::= { instantaneousVoltagePhNHarmonicsEntry 50071 } 

instHarmonicsRow10V3   OBJECT-TYPE
                SYNTAX      Unsigned32
                MAX-ACCESS  read-only
                STATUS      current
                DESCRIPTION "Voltage Ph-N Harmonic Row 10 of V3 (1/100 %)"
                ::= { instantaneousVoltagePhNHarmonicsEntry 50072 }


-- *******************************************************************************
-- ********************* MEASUREMENT INSTANTANEOUS VOLTAGE PH-PH HARMONICS TABLE *
-- *******************************************************************************
instantaneousVoltagePhPhHarmonicsTable       OBJECT-TYPE
                SYNTAX      SEQUENCE OF SeqInstantaneousVoltagePhPhHarmonicsEnt
                MAX-ACCESS  not-accessible
                STATUS      current
                DESCRIPTION "Instantaneous Voltage Phase-Neutral Harmonics metrology Table"
                ::= { productMetrology 85 }

instantaneousVoltagePhPhHarmonicsEntry       OBJECT-TYPE
                SYNTAX      SeqInstantaneousVoltagePhPhHarmonicsEnt
                MAX-ACCESS  not-accessible
                STATUS      current
                DESCRIPTION "Instantaneous Harmonics Data Table for given Product Index and Load Index"
                INDEX  { instVoltagePhPhHarmonicsModbusAddress }
                ::= { instantaneousVoltagePhPhHarmonicsTable 1 }

instVoltagePhPhHarmonicsModbusAddress    OBJECT-TYPE
                SYNTAX      Unsigned32(1..255)
                MAX-ACCESS  read-only
                STATUS      current
                DESCRIPTION "Modbus address of the product"
                ::= { instantaneousVoltagePhPhHarmonicsEntry 1 }

instVoltagePhPhHarmonicsProductIndex    OBJECT-TYPE
                SYNTAX      Unsigned32(1..33)  -- 32 Products + 1 Gateway
                MAX-ACCESS  read-only
                STATUS      current
                DESCRIPTION "Index of the Product to reach (1 = Gateway itself)"
                ::= { instantaneousVoltagePhPhHarmonicsEntry 5 }

instVoltagePhPhHarmonicsLoadRowStatus      OBJECT-TYPE
                SYNTAX       RowStatus
                MAX-ACCESS   read-create
                STATUS       current
                DESCRIPTION "The status of this conceptual row."
                ::= { instantaneousVoltagePhPhHarmonicsEntry 10 }

-- *******************
-- ** U12 Harmonics **
-- *******************
instHarmonicsRow02U12   OBJECT-TYPE
                SYNTAX      Unsigned32
                MAX-ACCESS  read-only
                STATUS      current
                DESCRIPTION "Voltage Ph-N Harmonic Row 2 of U12 (1/100 %)"
                ::= { instantaneousVoltagePhPhHarmonicsEntry 50091 } 
                
instHarmonicsRow03U12   OBJECT-TYPE
                SYNTAX      Unsigned32
                MAX-ACCESS  read-only
                STATUS      current
                DESCRIPTION "Voltage Ph-N Harmonic Row 3 of U12 (1/100 %)"
                ::= { instantaneousVoltagePhPhHarmonicsEntry 50092 } 

instHarmonicsRow04U12   OBJECT-TYPE
                SYNTAX      Unsigned32
                MAX-ACCESS  read-only
                STATUS      current
                DESCRIPTION "Voltage Ph-N Harmonic Row 4 of U12 (1/100 %)"
                ::= { instantaneousVoltagePhPhHarmonicsEntry 50093 } 

instHarmonicsRow05U12   OBJECT-TYPE
                SYNTAX      Unsigned32
                MAX-ACCESS  read-only
                STATUS      current
                DESCRIPTION "Voltage Ph-N Harmonic Row 5 of U12 (1/100 %)"
                ::= { instantaneousVoltagePhPhHarmonicsEntry 50094 } 

instHarmonicsRow06U12   OBJECT-TYPE
                SYNTAX      Unsigned32
                MAX-ACCESS  read-only
                STATUS      current
                DESCRIPTION "Voltage Ph-N Harmonic Row 6 of U12 (1/100 %)"
                ::= { instantaneousVoltagePhPhHarmonicsEntry 50095 } 
                
instHarmonicsRow07U12   OBJECT-TYPE
                SYNTAX      Unsigned32
                MAX-ACCESS  read-only
                STATUS      current
                DESCRIPTION "Voltage Ph-N Harmonic Row 7 of U12 (1/100 %)"
                ::= { instantaneousVoltagePhPhHarmonicsEntry 50096 } 

instHarmonicsRow08U12   OBJECT-TYPE
                SYNTAX      Unsigned32
                MAX-ACCESS  read-only
                STATUS      current
                DESCRIPTION "Voltage Ph-N Harmonic Row 8 of U12 (1/100 %)"
                ::= { instantaneousVoltagePhPhHarmonicsEntry 50097 } 

instHarmonicsRow09U12   OBJECT-TYPE
                SYNTAX      Unsigned32
                MAX-ACCESS  read-only
                STATUS      current
                DESCRIPTION "Voltage Ph-N Harmonic Row 9 of U12 (1/100 %)"
                ::= { instantaneousVoltagePhPhHarmonicsEntry 50098 } 

instHarmonicsRow10U12   OBJECT-TYPE
                SYNTAX      Unsigned32
                MAX-ACCESS  read-only
                STATUS      current
                DESCRIPTION "Voltage Ph-N Harmonic Row 10 of U12 (1/100 %)"
                ::= { instantaneousVoltagePhPhHarmonicsEntry 50099 } 

-- *******************
-- ** U23 Harmonics **
-- *******************
instHarmonicsRow02U23   OBJECT-TYPE
                SYNTAX      Unsigned32
                MAX-ACCESS  read-only
                STATUS      current
                DESCRIPTION "Voltage Ph-N Harmonic Row 2 of U23 (1/100 %)"
                ::= { instantaneousVoltagePhPhHarmonicsEntry 50118 } 
                
instHarmonicsRow03U23   OBJECT-TYPE
                SYNTAX      Unsigned32
                MAX-ACCESS  read-only
                STATUS      current
                DESCRIPTION "Voltage Ph-N Harmonic Row 3 of U23 (1/100 %)"
                ::= { instantaneousVoltagePhPhHarmonicsEntry 50119 } 

instHarmonicsRow04U23   OBJECT-TYPE
                SYNTAX      Unsigned32
                MAX-ACCESS  read-only
                STATUS      current
                DESCRIPTION "Voltage Ph-N Harmonic Row 4 of U23 (1/100 %)"
                ::= { instantaneousVoltagePhPhHarmonicsEntry 50120 } 

instHarmonicsRow05U23   OBJECT-TYPE
                SYNTAX      Unsigned32
                MAX-ACCESS  read-only
                STATUS      current
                DESCRIPTION "Voltage Ph-N Harmonic Row 5 of U23 (1/100 %)"
                ::= { instantaneousVoltagePhPhHarmonicsEntry 50121 } 

instHarmonicsRow06U23   OBJECT-TYPE
                SYNTAX      Unsigned32
                MAX-ACCESS  read-only
                STATUS      current
                DESCRIPTION "Voltage Ph-N Harmonic Row 6 of U23 (1/100 %)"
                ::= { instantaneousVoltagePhPhHarmonicsEntry 50122 } 
                
instHarmonicsRow07U23   OBJECT-TYPE
                SYNTAX      Unsigned32
                MAX-ACCESS  read-only
                STATUS      current
                DESCRIPTION "Voltage Ph-N Harmonic Row 7 of U23 (1/100 %)"
                ::= { instantaneousVoltagePhPhHarmonicsEntry 50123 } 

instHarmonicsRow08U23   OBJECT-TYPE
                SYNTAX      Unsigned32
                MAX-ACCESS  read-only
                STATUS      current
                DESCRIPTION "Voltage Ph-N Harmonic Row 8 of U23 (1/100 %)"
                ::= { instantaneousVoltagePhPhHarmonicsEntry 50124 } 

instHarmonicsRow09U23   OBJECT-TYPE
                SYNTAX      Unsigned32
                MAX-ACCESS  read-only
                STATUS      current
                DESCRIPTION "Voltage Ph-N Harmonic Row 9 of U23 (1/100 %)"
                ::= { instantaneousVoltagePhPhHarmonicsEntry 50125 } 

instHarmonicsRow10U23   OBJECT-TYPE
                SYNTAX      Unsigned32
                MAX-ACCESS  read-only
                STATUS      current
                DESCRIPTION "Voltage Ph-N Harmonic Row 10 of U23 (1/100 %)"
                ::= { instantaneousVoltagePhPhHarmonicsEntry 50126 } 

-- *******************
-- ** U31 Harmonics **
-- *******************
instHarmonicsRow02U31   OBJECT-TYPE
                SYNTAX      Unsigned32
                MAX-ACCESS  read-only
                STATUS      current
                DESCRIPTION "Voltage Ph-N Harmonic Row 2 of U31 (1/100 %)"
                ::= { instantaneousVoltagePhPhHarmonicsEntry 50145 } 
                
instHarmonicsRow03U31   OBJECT-TYPE
                SYNTAX      Unsigned32
                MAX-ACCESS  read-only
                STATUS      current
                DESCRIPTION "Voltage Ph-N Harmonic Row 3 of U31 (1/100 %)"
                ::= { instantaneousVoltagePhPhHarmonicsEntry 50146 } 

instHarmonicsRow04U31   OBJECT-TYPE
                SYNTAX      Unsigned32
                MAX-ACCESS  read-only
                STATUS      current
                DESCRIPTION "Voltage Ph-N Harmonic Row 4 of U31 (1/100 %)"
                ::= { instantaneousVoltagePhPhHarmonicsEntry 50147 } 

instHarmonicsRow05U31   OBJECT-TYPE
                SYNTAX      Unsigned32
                MAX-ACCESS  read-only
                STATUS      current
                DESCRIPTION "Voltage Ph-N Harmonic Row 5 of U31 (1/100 %)"
                ::= { instantaneousVoltagePhPhHarmonicsEntry 50148 } 

instHarmonicsRow06U31   OBJECT-TYPE
                SYNTAX      Unsigned32
                MAX-ACCESS  read-only
                STATUS      current
                DESCRIPTION "Voltage Ph-N Harmonic Row 6 of U31 (1/100 %)"
                ::= { instantaneousVoltagePhPhHarmonicsEntry 50149 } 
                
instHarmonicsRow07U31   OBJECT-TYPE
                SYNTAX      Unsigned32
                MAX-ACCESS  read-only
                STATUS      current
                DESCRIPTION "Voltage Ph-N Harmonic Row 7 of U31 (1/100 %)"
                ::= { instantaneousVoltagePhPhHarmonicsEntry 50150 } 

instHarmonicsRow08U31   OBJECT-TYPE
                SYNTAX      Unsigned32
                MAX-ACCESS  read-only
                STATUS      current
                DESCRIPTION "Voltage Ph-N Harmonic Row 8 of U31 (1/100 %)"
                ::= { instantaneousVoltagePhPhHarmonicsEntry 50151 } 

instHarmonicsRow09U31   OBJECT-TYPE
                SYNTAX      Unsigned32
                MAX-ACCESS  read-only
                STATUS      current
                DESCRIPTION "Voltage Ph-N Harmonic Row 9 of U31 (1/100 %)"
                ::= { instantaneousVoltagePhPhHarmonicsEntry 50152 } 

instHarmonicsRow10U31   OBJECT-TYPE
                SYNTAX      Unsigned32
                MAX-ACCESS  read-only
                STATUS      current
                DESCRIPTION "Voltage Ph-N Harmonic Row 10 of U31 (1/100 %)"
                ::= { instantaneousVoltagePhPhHarmonicsEntry 50153 }

-- *******************************************************************************
-- ********************* DIGITAL INPUT TABLE *************************************
inputDigitalTable       OBJECT-TYPE
                SYNTAX      SEQUENCE OF SeqDigInputEnt
                MAX-ACCESS  not-accessible
                STATUS      current
                DESCRIPTION "Table of Digital Inputs"
                ::= { productStates 1 }

inputDigitalEntry       OBJECT-TYPE
                SYNTAX      SeqDigInputEnt
                MAX-ACCESS  not-accessible
                STATUS      current
                DESCRIPTION "Digital Input Details for given Product Modbus Address and Input line"
                INDEX  { inputDigitalModbusAddress, inputDigitalLineIndex  }
                ::= { inputDigitalTable 1 }

inputDigitalModbusAddress    OBJECT-TYPE
                SYNTAX      Unsigned32(1..255)
                MAX-ACCESS  read-only
                STATUS      current
                DESCRIPTION "Modbus address of the product"
                ::= { inputDigitalEntry 1 }

inputDigitalProductIndex    OBJECT-TYPE
                SYNTAX      Unsigned32(1..33)  -- 32 Products + 1 Gateway
                MAX-ACCESS  read-only
                STATUS      current
                DESCRIPTION "Index of the Product to reach (1 = Gateway itself)"
                ::= { inputDigitalEntry 5 }

inputDigitalLineIndex       OBJECT-TYPE
                SYNTAX      Unsigned32(1..10)  -- 10 Inputs max
                MAX-ACCESS  read-only
                STATUS      current
                DESCRIPTION "Index of the Line to reach"
                ::= { inputDigitalEntry 7 }

inputDigitalRowStatus      OBJECT-TYPE
                SYNTAX       RowStatus
                MAX-ACCESS   read-create
                STATUS       current
                DESCRIPTION "The status of this conceptual row."
                ::= { inputDigitalEntry 10 }

inputDigitalFunction   OBJECT-TYPE
                SYNTAX      SocomecIOFunctions
                MAX-ACCESS  read-only
                STATUS      current
                DESCRIPTION "Input function"
                ::= { inputDigitalEntry 85086 } 
inputDigitalActivated   OBJECT-TYPE
                SYNTAX      Unsigned32(0..1)
                MAX-ACCESS  read-only
                STATUS      current
                DESCRIPTION "Line state is active"
                ::= { inputDigitalEntry 90002 } 
inputDigitalMode      OBJECT-TYPE
                SYNTAX      SocomecModeDigitalIO
                MAX-ACCESS  read-only
                STATUS      current
                DESCRIPTION "Input Normal state (0=NO / 1=NC)"
                ::= { inputDigitalEntry 90003 } 

-- *******************************************************************************
-- ********************* DIGITAL OUTPUT TABLE ************************************
outputDigitalTable       OBJECT-TYPE
                SYNTAX      SEQUENCE OF SeqDigOutputEnt
                MAX-ACCESS  not-accessible
                STATUS      current
                DESCRIPTION "Table of Digital Outputs"
                ::= { productStates 2 }

outputDigitalEntry       OBJECT-TYPE
                SYNTAX      SeqDigOutputEnt
                MAX-ACCESS  not-accessible
                STATUS      current
                DESCRIPTION "Digital Output Details for given Product Modbus Address and Output line"
                INDEX  { outputDigitalModbusAddress, outputDigitalLineIndex  }
                ::= { outputDigitalTable 1 }

outputDigitalModbusAddress    OBJECT-TYPE
                SYNTAX      Unsigned32(1..255)
                MAX-ACCESS  read-only
                STATUS      current
                DESCRIPTION "Modbus address of the product"
                ::= { outputDigitalEntry 1 }

outputDigitalProductIndex    OBJECT-TYPE
                SYNTAX      Unsigned32(1..33)  -- 32 Products + 1 Gateway
                MAX-ACCESS  read-only
                STATUS      current
                DESCRIPTION "Index of the Product to reach (1 = Gateway itself)"
                ::= { outputDigitalEntry 5 }

outputDigitalLineIndex       OBJECT-TYPE
                SYNTAX      Unsigned32(1..8)  -- 8 Outputs max
                MAX-ACCESS  read-only
                STATUS      current
                DESCRIPTION "Index of the Line to reach"
                ::= { outputDigitalEntry 7 }

outputDigitalRowStatus      OBJECT-TYPE
                SYNTAX       RowStatus
                MAX-ACCESS   read-create
                STATUS       current
                DESCRIPTION "The status of this conceptual row."
                ::= { outputDigitalEntry 10 }

outputDigitalFunction   OBJECT-TYPE
                SYNTAX      SocomecIOFunctions
                MAX-ACCESS  read-only
                STATUS      current
                DESCRIPTION "output function"
                ::= { outputDigitalEntry 85102 } 
outputDigitalActivated   OBJECT-TYPE
                SYNTAX      Unsigned32(0..1)
                MAX-ACCESS  read-only
                STATUS      current
                DESCRIPTION "Line state is active"
                ::= { outputDigitalEntry 90006 } 
outputDigitalMode  OBJECT-TYPE
                SYNTAX      SocomecModeDigitalIO
                MAX-ACCESS  read-only
                STATUS      current
                DESCRIPTION "Output Normal state (0=NO / 1=NC)"
                ::= { outputDigitalEntry 90024 } 
outputDigitalCmdDeact   OBJECT-TYPE
                SYNTAX      Unsigned32(0..1)
                MAX-ACCESS  read-write
                STATUS      current
                DESCRIPTION "Command to deactive the output"
                ::= { outputDigitalEntry 85177 } 
outputDigitalCmdAct   OBJECT-TYPE
                SYNTAX      Unsigned32(0..1)
                MAX-ACCESS  read-write
                STATUS      current
                DESCRIPTION "Command to active the output"
                ::= { outputDigitalEntry 85178 } 


-- *******************************************************************************
-- ********************* PROTECTION TABLE ****************************************
protectionTable OBJECT-TYPE
                SYNTAX      SEQUENCE OF SeqProtectionEnt
                MAX-ACCESS  not-accessible
                STATUS      current
                DESCRIPTION "Table of Protections"
                ::= { productStates 3 }

protectionEntry       OBJECT-TYPE
                SYNTAX      SeqProtectionEnt
                MAX-ACCESS  not-accessible
                STATUS      current
                DESCRIPTION "Protection for given Product Modbus Address and protect line"
                INDEX  { protectionModbusAddress, protectionProtectIndex }				
                ::= { protectionTable 1 }

protectionModbusAddress    OBJECT-TYPE
                SYNTAX      Unsigned32(1..255)
                MAX-ACCESS  read-only
                STATUS      current
                DESCRIPTION "Modbus address of the product"
                ::= { protectionEntry 1 }

protectionProductIndex    OBJECT-TYPE
                SYNTAX      Unsigned32(1..33)  -- 32 Products + 1 Gateway
                MAX-ACCESS  read-only
                STATUS      current
                DESCRIPTION "Index of the Product to reach (1 = Gateway itself)"
                ::= { protectionEntry 5 }

protectionProtectIndex       OBJECT-TYPE
                SYNTAX      Unsigned32(1..6)  -- 6 Protects max
                MAX-ACCESS  read-only
                STATUS      current
                DESCRIPTION "Index of the protect line to reach"
                ::= { protectionEntry 7 }
				
protectionRowStatus      OBJECT-TYPE
                SYNTAX       RowStatus
                MAX-ACCESS   read-create
                STATUS       current
                DESCRIPTION "The status of this conceptual row."
                ::= { protectionEntry 10 }

protectionPosition       OBJECT-TYPE
                SYNTAX      SocomecBreakerPosition
                MAX-ACCESS  read-only
                STATUS      current
                DESCRIPTION "Position state"
                ::= { protectionEntry 90007 }
protectionTripStatus       OBJECT-TYPE
                SYNTAX      SocomecTripStatus
                MAX-ACCESS  read-only
                STATUS      current
                DESCRIPTION "Trip status"
                ::= { protectionEntry 90008 }
protectionDefectiveDeviceStatus       OBJECT-TYPE
                SYNTAX      SocomecBreakerFault
                MAX-ACCESS  read-only
                STATUS      current
                DESCRIPTION "Status of the protection device"
                ::= { protectionEntry 136012 }
protectionTripCause       OBJECT-TYPE
                SYNTAX      SocomecTripCause
                MAX-ACCESS  read-only
                STATUS      current
                DESCRIPTION "Trip cause of the protection"
                ::= { protectionEntry 90136 }
protectionRCDDeviceFault       OBJECT-TYPE
                SYNTAX      SocomecBreakerFault
                MAX-ACCESS  read-only
                STATUS      current
                DESCRIPTION "Residual currend device fault"
                ::= { protectionEntry 90137 }
protectionPole1Position       OBJECT-TYPE
                SYNTAX      SocomecBreakerPosition
                MAX-ACCESS  read-only
                STATUS      current
                DESCRIPTION "Position of Pole 1"
                ::= { protectionEntry 136003 }
protectionPole2Position       OBJECT-TYPE
                SYNTAX      SocomecBreakerPosition
                MAX-ACCESS  read-only
                STATUS      current
                DESCRIPTION "Position of Pole 2"
                ::= { protectionEntry 136004 }
protectionPole3Position       OBJECT-TYPE
                SYNTAX      SocomecBreakerPosition
                MAX-ACCESS  read-only
                STATUS      current
                DESCRIPTION "Position of Pole 3"
                ::= { protectionEntry 136005 }

protectionTotalOperationCount       OBJECT-TYPE
                SYNTAX      Unsigned32
                MAX-ACCESS  read-only
                STATUS      current
                DESCRIPTION "Total Count"
                ::= { protectionEntry 136011 }
protectionLowLoadOperationCount       OBJECT-TYPE
                SYNTAX      Unsigned32
                MAX-ACCESS  read-only
                STATUS      current
                DESCRIPTION "Low load Count"
                ::= { protectionEntry 136007 }
protectionOnLoadOperationCount       OBJECT-TYPE
                SYNTAX      Unsigned32
                MAX-ACCESS  read-only
                STATUS      current
                DESCRIPTION "On load Count"
                ::= { protectionEntry 136008 }
protectionOverLoadOperationCount       OBJECT-TYPE
                SYNTAX      Unsigned32
                MAX-ACCESS  read-only
                STATUS      current
                DESCRIPTION "Over load Count"
                ::= { protectionEntry 136009 }
protectionTripCount       OBJECT-TYPE
                SYNTAX      Unsigned32
                MAX-ACCESS  read-only
                STATUS      current
                DESCRIPTION "Trip Count"
                ::= { protectionEntry 90009 }
protectionLastTripDate       OBJECT-TYPE
                SYNTAX      Unsigned32
                MAX-ACCESS  read-only
                STATUS      current
                DESCRIPTION "Last Trip Date"
                ::= { protectionEntry 90072 }


-- *******************************************************************************
-- ********************* ANALOG INPUT TABLE **************************************
inputAnalogTable       OBJECT-TYPE
                SYNTAX      SEQUENCE OF SeqAnaInputEnt
                MAX-ACCESS  not-accessible
                STATUS      current
                DESCRIPTION "Table of Analog Inputs"
                ::= { productStates 4 }

inputAnalogEntry       OBJECT-TYPE
                SYNTAX      SeqAnaInputEnt
                MAX-ACCESS  not-accessible
                STATUS      current
                DESCRIPTION "Analog Input Details for given Product Modbus Address and Input line"
                INDEX  { inputAnalogModbusAddress, inputAnalogLineIndex  }
                ::= { inputAnalogTable 1 }

inputAnalogModbusAddress    OBJECT-TYPE
                SYNTAX      Unsigned32(1..255)
                MAX-ACCESS  read-only
                STATUS      current
                DESCRIPTION "Modbus address of the product"
                ::= { inputAnalogEntry 1 }

inputAnalogProductIndex    OBJECT-TYPE
                SYNTAX      Unsigned32(1..33)  -- 32 Products + 1 Gateway
                MAX-ACCESS  read-only
                STATUS      current
                DESCRIPTION "Index of the Product to reach (1 = Gateway itself)"
                ::= { inputAnalogEntry 5 }

inputAnalogLineIndex       OBJECT-TYPE
                SYNTAX      Unsigned32(1..10)  -- 10 Inputs max
                MAX-ACCESS  read-only
                STATUS      current
                DESCRIPTION "Index of the Line to reach"
                ::= { inputAnalogEntry 7 }

inputAnalogRowStatus      OBJECT-TYPE
                SYNTAX       RowStatus
                MAX-ACCESS   read-create
                STATUS       current
                DESCRIPTION "The status of this conceptual row."
                ::= { inputAnalogEntry 10 }

inputAnalogPresentValue   OBJECT-TYPE
                SYNTAX      Integer32
                MAX-ACCESS  read-only
                STATUS      current
                DESCRIPTION "Present Value"
                ::= { inputAnalogEntry 65004 } 
inputAnalogAverageValue   OBJECT-TYPE
                SYNTAX      Integer32
                MAX-ACCESS  read-only
                STATUS      current
                DESCRIPTION "Average Value"
                ::= { inputAnalogEntry 65093 }                 
inputAnalogUnit           OBJECT-TYPE
                SYNTAX      DisplayString (SIZE (0..255))
                MAX-ACCESS  read-only
                STATUS      current
                DESCRIPTION "Unit of the analog input meter"
                ::= { inputAnalogEntry 65027 }
inputAnalogMode OBJECT-TYPE
                SYNTAX      SocomecModeAnalogIO
                MAX-ACCESS  read-only
                STATUS      current
                DESCRIPTION "Analog Mode (0=0-20mA / 1=4-20mA)"
                ::= { inputAnalogEntry 65026 } 

-- *******************************************************************************
-- ********************* ANALOG OUTPUT TABLE *************************************
outputAnalogTable       OBJECT-TYPE
                SYNTAX      SEQUENCE OF SeqAnaOutputEnt
                MAX-ACCESS  not-accessible
                STATUS      current
                DESCRIPTION "Table of Analog Outputs"
                ::= { productStates 5 }

outputAnalogEntry       OBJECT-TYPE
                SYNTAX      SeqAnaOutputEnt
                MAX-ACCESS  not-accessible
                STATUS      current
                DESCRIPTION "Analog Output Details for given Product Modbus Address and Output line"
                INDEX  { outputAnalogModbusAddress, outputAnalogLineIndex  }
                ::= { outputAnalogTable 1 }

outputAnalogModbusAddress    OBJECT-TYPE
                SYNTAX      Unsigned32(1..255)
                MAX-ACCESS  read-only
                STATUS      current
                DESCRIPTION "Modbus address of the product"
                ::= { outputAnalogEntry 1 }

outputAnalogProductIndex    OBJECT-TYPE
                SYNTAX      Unsigned32(1..33)  -- 32 Products + 1 Gateway
                MAX-ACCESS  read-only
                STATUS      current
                DESCRIPTION "Index of the Product to reach (1 = Gateway itself)"
                ::= { outputAnalogEntry 5 }

outputAnalogLineIndex       OBJECT-TYPE
                SYNTAX      Unsigned32(1..10)  -- 10 Outputs max
                MAX-ACCESS  read-only
                STATUS      current
                DESCRIPTION "Index of the Line to reach"
                ::= { outputAnalogEntry 7 }

outputAnalogRowStatus      OBJECT-TYPE
                SYNTAX       RowStatus
                MAX-ACCESS   read-create
                STATUS       current
                DESCRIPTION "The status of this conceptual row."
                ::= { outputAnalogEntry 10 }

outputAnalogVariableService   OBJECT-TYPE
                SYNTAX      Unsigned32(0..1)
                MAX-ACCESS  read-only
                STATUS      current
                DESCRIPTION "Present Value"
                ::= { outputAnalogEntry 65059 } 
outputAnalogVariableInstance   OBJECT-TYPE
                SYNTAX      Unsigned32(0..1)
                MAX-ACCESS  read-only
                STATUS      current
                DESCRIPTION "Average Value"
                ::= { outputAnalogEntry 65060 }                 

outputAnalogMode OBJECT-TYPE
                SYNTAX      SocomecModeAnalogIO
                MAX-ACCESS  read-only
                STATUS      current
                DESCRIPTION "Analog Type (0=0-20mA / 1=4-20mA)"
                ::= { outputAnalogEntry 65056 } 
         

-- *******************************************************************************
-- ********************* Alarm Table *********************************************

almInProgressTable       OBJECT-TYPE
                SYNTAX      SEQUENCE OF SeqAlmInProgressEnt
                MAX-ACCESS  not-accessible
                STATUS      current
                DESCRIPTION "Table of Analog Outputs"
                ::= { productStates 6 }

almInProgressEntry       OBJECT-TYPE
                SYNTAX      SeqAlmInProgressEnt
                MAX-ACCESS  not-accessible
                STATUS      current
                DESCRIPTION "Analog Output Details for given Product Modbus Address and Output line"
                INDEX  { almInProgressIndex }
                ::= { almInProgressTable 1 }

almInProgressIndex    OBJECT-TYPE
                SYNTAX      SocomecAlarmType
                MAX-ACCESS  read-only
                STATUS      current
                DESCRIPTION "Index of the product"
                ::= { almInProgressEntry 1 }

almInProgressNumber    OBJECT-TYPE      
                SYNTAX      Unsigned32(1..255)
                MAX-ACCESS  read-only
                STATUS      current
                DESCRIPTION "Number of the alarm in progress"
                ::= { almInProgressEntry 2 }

almInProgressRowStatus      OBJECT-TYPE
                SYNTAX       RowStatus
                MAX-ACCESS   read-create
                STATUS       current
                DESCRIPTION "The status of this conceptual row."
                ::= { almInProgressEntry 10 }

-- *******************************************************************************
-- ********************* DC TABLE ************************************************
metroDCTable       OBJECT-TYPE
                SYNTAX      SEQUENCE OF SeqMetroDCEnt
                MAX-ACCESS  not-accessible
                STATUS      current
                DESCRIPTION "DC metrology Table"
                ::= { productMetrology 90 }

metroDCEntry       OBJECT-TYPE
                SYNTAX      SeqMetroDCEnt
                MAX-ACCESS  not-accessible
                STATUS      current
                DESCRIPTION "DC Metrology Data Table for given Product Modbus Address and Load Index"
                INDEX  { dcModbusAddress, dcLoadIndex  }
                ::= { metroDCTable 1 }

dcModbusAddress    OBJECT-TYPE
                SYNTAX      Unsigned32(1..255)
                MAX-ACCESS  read-only
                STATUS      current
                DESCRIPTION "Modbus address of the product"
                ::= { metroDCEntry 1 }

dcProductIndex    OBJECT-TYPE
                SYNTAX      Unsigned32(1..33)  -- 32 Products + 1 Gateway
                MAX-ACCESS  read-only
                STATUS      current
                DESCRIPTION "Index of the Product to reach (1 = Gateway itself)"
                ::= { metroDCEntry 5 }

dcLoadIndex       OBJECT-TYPE
                SYNTAX      Unsigned32 (1..16)  -- 6 Loads + 10 MultiFluids
                MAX-ACCESS  read-only
                STATUS      current
                DESCRIPTION "Index of the Load to reach"
                ::= { metroDCEntry 6 }

dcLoadRowStatus      OBJECT-TYPE
                SYNTAX       RowStatus
                MAX-ACCESS   read-create
                STATUS       current
                DESCRIPTION "The status of this conceptual row."
                ::= { metroDCEntry 10 }

dcInstIrms      OBJECT-TYPE
                SYNTAX      Unsigned32
                MAX-ACCESS  read-only
                STATUS      current
                DESCRIPTION "Instantaneous Rms Current (mA)"
                ::= { metroDCEntry 10176 }  

dcInstIdc       OBJECT-TYPE
                SYNTAX      Integer32
                MAX-ACCESS  read-only
                STATUS      current
                DESCRIPTION "Instantaneous DC Current (mA)"
                ::= { metroDCEntry 10177 }

dcInstIripple   OBJECT-TYPE
                SYNTAX      Unsigned32
                MAX-ACCESS  read-only
                STATUS      current
                DESCRIPTION "Instantaneous Ripple Current (mA)"
                ::= { metroDCEntry 10178 }  
                
dcAvgIrms       OBJECT-TYPE
                SYNTAX      Unsigned32
                MAX-ACCESS  read-only
                STATUS      current
                DESCRIPTION "Average Rms Current (mA)"
                ::= { metroDCEntry 10179 }

dcAvgIdc        OBJECT-TYPE
                SYNTAX      Integer32
                MAX-ACCESS  read-only
                STATUS      current
                DESCRIPTION "Average DC Current (mA)"
                ::= { metroDCEntry 10180 }

dcAvgIripple    OBJECT-TYPE
                SYNTAX      Unsigned32
                MAX-ACCESS  read-only
                STATUS      current
                DESCRIPTION "Average Ripple Current (mA)"
                ::= { metroDCEntry 10181 }
                
dcMaxInstIrms      OBJECT-TYPE
                SYNTAX      Unsigned32
                MAX-ACCESS  read-only
                STATUS      current
                DESCRIPTION "Max Instantaneous Rms Current (mA)"
                ::= { metroDCEntry 10268 }  
dcMaxInstIrmsDate      OBJECT-TYPE
                SYNTAX      Unsigned32
                MAX-ACCESS  read-only
                STATUS      current
                DESCRIPTION "Max Instantaneous Rms Current Date"
                ::= { metroDCEntry 10269 }  

dcMaxInstIdc       OBJECT-TYPE
                SYNTAX      Integer32
                MAX-ACCESS  read-only
                STATUS      current
                DESCRIPTION "Max Instantaneous DC Current (mA)"
                ::= { metroDCEntry 10270 }  
dcMaxInstIdcDate       OBJECT-TYPE
                SYNTAX      Unsigned32
                MAX-ACCESS  read-only
                STATUS      current
                DESCRIPTION "Max Instantaneous DC Current Date"
                ::= { metroDCEntry 10271 }

dcMaxInstIripple   OBJECT-TYPE
                SYNTAX      Unsigned32
                MAX-ACCESS  read-only
                STATUS      current
                DESCRIPTION "Max Instantaneous Ripple Current (mA)"
                ::= { metroDCEntry 10272 }  
dcMaxInstIrippleDate   OBJECT-TYPE
                SYNTAX      Unsigned32
                MAX-ACCESS  read-only
                STATUS      current
                DESCRIPTION "Max Instantaneous Ripple Current Date"
                ::= { metroDCEntry 10273 }  
                
dcMinInstIrms      OBJECT-TYPE
                SYNTAX      Unsigned32
                MAX-ACCESS  read-only
                STATUS      current
                DESCRIPTION "Min Instantaneous Rms Current (mA)"
                ::= { metroDCEntry 10274 }  
dcMinInstIrmsDate      OBJECT-TYPE
                SYNTAX      Unsigned32
                MAX-ACCESS  read-only
                STATUS      current
                DESCRIPTION "Min Instantaneous Rms Current Date"
                ::= { metroDCEntry 10275 }  

dcMinInstIdc       OBJECT-TYPE
                SYNTAX      Integer32
                MAX-ACCESS  read-only
                STATUS      current
                DESCRIPTION "Min Instantaneous DC Current (mA)"
                ::= { metroDCEntry 10276 }
dcMinInstIdcDate       OBJECT-TYPE
                SYNTAX      Unsigned32
                MAX-ACCESS  read-only
                STATUS      current
                DESCRIPTION "Min Instantaneous DC Current Date"
                ::= { metroDCEntry 10277 }

dcMinInstIripple   OBJECT-TYPE
                SYNTAX      Unsigned32
                MAX-ACCESS  read-only
                STATUS      current
                DESCRIPTION "Min Instantaneous Ripple Current (mA)"
                ::= { metroDCEntry 10278 }
dcMinInstIrippleDate   OBJECT-TYPE
                SYNTAX      Unsigned32
                MAX-ACCESS  read-only
                STATUS      current
                DESCRIPTION "Min Instantaneous Ripple Current Date"
                ::= { metroDCEntry 10279 } 
                
dcMaxAvgIrms      OBJECT-TYPE
                SYNTAX      Unsigned32
                MAX-ACCESS  read-only
                STATUS      current
                DESCRIPTION "Max Average Rms Current (mA)"
                ::= { metroDCEntry 10281 }  
dcMaxAvgIrmsDate      OBJECT-TYPE
                SYNTAX      Unsigned32
                MAX-ACCESS  read-only
                STATUS      current
                DESCRIPTION "Max Average Rms Current Date"
                ::= { metroDCEntry 10282 }  

dcMaxAvgIdc       OBJECT-TYPE
                SYNTAX      Integer32
                MAX-ACCESS  read-only
                STATUS      current
                DESCRIPTION "Max Average DC Current (mA)"
                ::= { metroDCEntry 10283 }
dcMaxAvgIdcDate       OBJECT-TYPE
                SYNTAX      Unsigned32
                MAX-ACCESS  read-only
                STATUS      current
                DESCRIPTION "Max Average DC Current Date"
                ::= { metroDCEntry 10284 }

dcMaxAvgIripple   OBJECT-TYPE
                SYNTAX      Unsigned32
                MAX-ACCESS  read-only
                STATUS      current
                DESCRIPTION "Max Average Ripple Current (mA)"
                ::= { metroDCEntry 10285 }  
dcMaxAvgIrippleDate   OBJECT-TYPE
                SYNTAX      Unsigned32
                MAX-ACCESS  read-only
                STATUS      current
                DESCRIPTION "Max Average Ripple Current Date"
                ::= { metroDCEntry 10286 }  
                
dcMinAvgIrms      OBJECT-TYPE
                SYNTAX      Unsigned32
                MAX-ACCESS  read-only
                STATUS      current
                DESCRIPTION "Min Average Rms Current (mA)"
                ::= { metroDCEntry 10287 }  
dcMinAvgIrmsDate      OBJECT-TYPE
                SYNTAX      Unsigned32
                MAX-ACCESS  read-only
                STATUS      current
                DESCRIPTION "Min Average Rms Current Date"
                ::= { metroDCEntry 10288 }  

dcMinAvgIdc       OBJECT-TYPE
                SYNTAX      Integer32
                MAX-ACCESS  read-only
                STATUS      current
                DESCRIPTION "Min Average DC Current (mA)"
                ::= { metroDCEntry 10289 }
dcMinAvgIdcDate       OBJECT-TYPE
                SYNTAX      Unsigned32
                MAX-ACCESS  read-only
                STATUS      current
                DESCRIPTION "Min Average DC Current Date"
                ::= { metroDCEntry 10290 }

dcMinAvgIripple   OBJECT-TYPE
                SYNTAX      Unsigned32
                MAX-ACCESS  read-only
                STATUS      current
                DESCRIPTION "Min Average Ripple Current (mA)"
                ::= { metroDCEntry 10291 } 
dcMinAvgIrippleDate   OBJECT-TYPE
                SYNTAX      Unsigned32
                MAX-ACCESS  read-only
                STATUS      current
                DESCRIPTION "Min Average Ripple Current Date"
                ::= { metroDCEntry 10292 } 
                
dcAvgDateLastInstance   OBJECT-TYPE
                SYNTAX      Unsigned32
                MAX-ACCESS  read-only
                STATUS      current
                DESCRIPTION "Date of last instance (measured point)"
                ::= { metroDCEntry 45004 } 
                
dcInstTotalPowerActive      OBJECT-TYPE
                SYNTAX      Integer32
                MAX-ACCESS  read-only
                STATUS      current
                DESCRIPTION "Instantaneous Total Active Power (W)"
                ::= { metroDCEntry 80003 }
                
dcAvgTotalPowerActive      OBJECT-TYPE
                SYNTAX      Integer32
                MAX-ACCESS  read-only
                STATUS      current
                DESCRIPTION "Average Total Active Power (W)"
                ::= { metroDCEntry 80031 }
                
dcMinInstTotalPowerActive      OBJECT-TYPE
                SYNTAX      Integer32
                MAX-ACCESS  read-only
                STATUS      current
                DESCRIPTION "Min Instantaneous Total Active Power (W)"
                ::= { metroDCEntry 80062 }
dcMinInstTotalPowerActiveDate      OBJECT-TYPE
                SYNTAX      Unsigned32
                MAX-ACCESS  read-only
                STATUS      current
                DESCRIPTION "Min Instantaneous Total Active Power Date"
                ::= { metroDCEntry 80063 }
                
dcMaxInstTotalPowerActive      OBJECT-TYPE
                SYNTAX      Integer32
                MAX-ACCESS  read-only
                STATUS      current
                DESCRIPTION "Max Instantaneous Total Active Power (W)"
                ::= { metroDCEntry 80102 }
dcMaxInstTotalPowerActiveDate      OBJECT-TYPE
                SYNTAX      Unsigned32
                MAX-ACCESS  read-only
                STATUS      current
                DESCRIPTION "Max Instantaneous Total Active Power Date"
                ::= { metroDCEntry 80103 }
                
dcMinAvgTotalPowerActive      OBJECT-TYPE
                SYNTAX      Integer32
                MAX-ACCESS  read-only
                STATUS      current
                DESCRIPTION "Min Average Total Active Power (W)"
                ::= { metroDCEntry 80142 }
dcMinAvgTotalPowerActiveDate      OBJECT-TYPE
                SYNTAX      Unsigned32
                MAX-ACCESS  read-only
                STATUS      current
                DESCRIPTION "Min Average Total Active Power Date"
                ::= { metroDCEntry 80143 }
                
dcMaxAvgTotalPowerActive      OBJECT-TYPE
                SYNTAX      Integer32
                MAX-ACCESS  read-only
                STATUS      current
                DESCRIPTION "Max Average Total Active Power (W)"
                ::= { metroDCEntry 80182 }
dcMaxAvgTotalPowerActiveDate      OBJECT-TYPE
                SYNTAX      Unsigned32
                MAX-ACCESS  read-only
                STATUS      current
                DESCRIPTION "Max Average Total Active Power Date"
                ::= { metroDCEntry 80183 }
                
dcInstVrms      OBJECT-TYPE
                SYNTAX      Unsigned32
                MAX-ACCESS  read-only
                STATUS      current
                DESCRIPTION "Instantaneous Rms Voltage (1/100 V)"
                ::= { metroDCEntry 110338 }  

dcInstVdc       OBJECT-TYPE
                SYNTAX      Integer32
                MAX-ACCESS  read-only
                STATUS      current
                DESCRIPTION "Instantaneous DC Voltage (1/100 V)"
                ::= { metroDCEntry 110339 }

dcInstVripple   OBJECT-TYPE
                SYNTAX      Unsigned32
                MAX-ACCESS  read-only
                STATUS      current
                DESCRIPTION "Instantaneous Ripple Voltage (1/100 V)"
                ::= { metroDCEntry 110340 }  
                
dcAvgVrms      OBJECT-TYPE
                SYNTAX      Unsigned32
                MAX-ACCESS  read-only
                STATUS      current
                DESCRIPTION "Average Rms Voltage (1/100 V)"
                ::= { metroDCEntry 110343 }

dcAvgVdc       OBJECT-TYPE
                SYNTAX      Integer32
                MAX-ACCESS  read-only
                STATUS      current
                DESCRIPTION "Average DC Voltage (1/100 V)"
                ::= { metroDCEntry 110344 }

dcAvgVripple   OBJECT-TYPE
                SYNTAX      Unsigned32
                MAX-ACCESS  read-only
                STATUS      current
                DESCRIPTION "Average Ripple Voltage (1/100 V)"
                ::= { metroDCEntry 110345 }
                
dcMaxInstVrms      OBJECT-TYPE
                SYNTAX      Unsigned32
                MAX-ACCESS  read-only
                STATUS      current
                DESCRIPTION "Max Instantaneous Rms Voltage (1/100 V)"
                ::= { metroDCEntry 110416 }  
dcMaxInstVrmsDate      OBJECT-TYPE
                SYNTAX      Unsigned32
                MAX-ACCESS  read-only
                STATUS      current
                DESCRIPTION "Max Instantaneous Rms Voltage Date"
                ::= { metroDCEntry 110417 }  

dcMaxInstVdc       OBJECT-TYPE
                SYNTAX      Integer32
                MAX-ACCESS  read-only
                STATUS      current
                DESCRIPTION "Max Instantaneous DC Voltage (1/100 V)"
                ::= { metroDCEntry 110418 }
dcMaxInstVdcDate       OBJECT-TYPE
                SYNTAX      Unsigned32
                MAX-ACCESS  read-only
                STATUS      current
                DESCRIPTION "Max Instantaneous DC Voltage Date"
                ::= { metroDCEntry 110419 }

dcMaxInstVripple   OBJECT-TYPE
                SYNTAX      Unsigned32
                MAX-ACCESS  read-only
                STATUS      current
                DESCRIPTION "Max Instantaneous Ripple Voltage (1/100 V)"
                ::= { metroDCEntry 110420 }  
dcMaxInstVrippleDate   OBJECT-TYPE
                SYNTAX      Unsigned32
                MAX-ACCESS  read-only
                STATUS      current
                DESCRIPTION "Max Instantaneous Ripple Voltage Date"
                ::= { metroDCEntry 110421 }  
                
dcMinInstVrms      OBJECT-TYPE
                SYNTAX      Unsigned32
                MAX-ACCESS  read-only
                STATUS      current
                DESCRIPTION "Min Instantaneous Rms Voltage (1/100 V)"
                ::= { metroDCEntry 110422 } 
dcMinInstVrmsDate      OBJECT-TYPE
                SYNTAX      Unsigned32
                MAX-ACCESS  read-only
                STATUS      current
                DESCRIPTION "Min Instantaneous Rms Voltage Date"
                ::= { metroDCEntry 110423 }  

dcMinInstVdc       OBJECT-TYPE
                SYNTAX      Integer32
                MAX-ACCESS  read-only
                STATUS      current
                DESCRIPTION "Min Instantaneous DC Voltage (1/100 V)"
                ::= { metroDCEntry 110424 }
dcMinInstVdcDate       OBJECT-TYPE
                SYNTAX      Unsigned32
                MAX-ACCESS  read-only
                STATUS      current
                DESCRIPTION "Min Instantaneous DC Voltage Date"
                ::= { metroDCEntry 110425 }

dcMinInstVripple   OBJECT-TYPE
                SYNTAX      Unsigned32
                MAX-ACCESS  read-only
                STATUS      current
                DESCRIPTION "Min Instantaneous Ripple Voltage (1/100 V)"
                ::= { metroDCEntry 110426 }  
dcMinInstVrippleDate   OBJECT-TYPE
                SYNTAX      Unsigned32
                MAX-ACCESS  read-only
                STATUS      current
                DESCRIPTION "Min Instantaneous Ripple Voltage Date"
                ::= { metroDCEntry 110427 }  
         
dcMaxAvgVrms      OBJECT-TYPE
                SYNTAX      Unsigned32
                MAX-ACCESS  read-only
                STATUS      current
                DESCRIPTION "Max Average Rms Voltage (1/100 V)"
                ::= { metroDCEntry 110429 }  
dcMaxAvgVrmsDate      OBJECT-TYPE
                SYNTAX      Unsigned32
                MAX-ACCESS  read-only
                STATUS      current
                DESCRIPTION "Max Average Rms Voltage Date"
                ::= { metroDCEntry 110430 }  

dcMaxAvgVdc       OBJECT-TYPE
                SYNTAX      Integer32
                MAX-ACCESS  read-only
                STATUS      current
                DESCRIPTION "Max Average DC Voltage (1/100 V)"
                ::= { metroDCEntry 110431 }
dcMaxAvgVdcDate       OBJECT-TYPE
                SYNTAX      Unsigned32
                MAX-ACCESS  read-only
                STATUS      current
                DESCRIPTION "Max Average DC Voltage Date"
                ::= { metroDCEntry 110432 }

dcMaxAvgVripple   OBJECT-TYPE
                SYNTAX      Unsigned32
                MAX-ACCESS  read-only
                STATUS      current
                DESCRIPTION "Max Average Ripple Voltage (1/100 V)"
                ::= { metroDCEntry 110433 }  
dcMaxAvgVrippleDate   OBJECT-TYPE
                SYNTAX      Unsigned32
                MAX-ACCESS  read-only
                STATUS      current
                DESCRIPTION "Max Average Ripple Voltage Date"
                ::= { metroDCEntry 110434 }  
                
dcMinAvgVrms      OBJECT-TYPE
                SYNTAX      Unsigned32
                MAX-ACCESS  read-only
                STATUS      current
                DESCRIPTION "Min Average Rms Voltage (1/100 V)"
                ::= { metroDCEntry 110435 } 
dcMinAvgVrmsDate      OBJECT-TYPE
                SYNTAX      Unsigned32
                MAX-ACCESS  read-only
                STATUS      current
                DESCRIPTION "Min Average Rms Voltage Date"
                ::= { metroDCEntry 110436 }  

dcMinAvgVdc       OBJECT-TYPE
                SYNTAX      Integer32
                MAX-ACCESS  read-only
                STATUS      current
                DESCRIPTION "Min Average DC Voltage (1/100 V)"
                ::= { metroDCEntry 110437 }
dcMinAvgVdcDate       OBJECT-TYPE
                SYNTAX      Unsigned32
                MAX-ACCESS  read-only
                STATUS      current
                DESCRIPTION "Min Average DC Voltage Date"
                ::= { metroDCEntry 110438 }

dcMinAvgVripple   OBJECT-TYPE
                SYNTAX      Unsigned32
                MAX-ACCESS  read-only
                STATUS      current
                DESCRIPTION "Min Average Ripple Voltage (1/100 V)"
                ::= { metroDCEntry 110439 }  
dcMinAvgVrippleDate   OBJECT-TYPE
                SYNTAX      Unsigned32
                MAX-ACCESS  read-only
                STATUS      current
                DESCRIPTION "Min Average Ripple Voltage Date"
                ::= { metroDCEntry 110440 }  
         
-- *******************************************************************************
-- ********************* ATS METRO TABLE (LEGAY TABLE) ***************************
atsMetroLegacyTable   OBJECT-TYPE
                SYNTAX      SEQUENCE OF SeqAtsMetroLegacyEnt
                MAX-ACCESS  not-accessible
                STATUS      current
                DESCRIPTION "Ats Metrology Table (Legacy Table)"
                ::= { productAts 10 }

atsMetroLegacyEntry   OBJECT-TYPE
                SYNTAX      SeqAtsMetroLegacyEnt
                MAX-ACCESS  not-accessible
                STATUS      current
                DESCRIPTION "Ats Metrology Details for given Product Index"
                INDEX  { atsMetroLegacyModbusAddress }
                ::= { atsMetroLegacyTable 1 }

atsMetroLegacyModbusAddress    OBJECT-TYPE
                SYNTAX      Unsigned32(1..255)
                MAX-ACCESS  read-only
                STATUS      current
                DESCRIPTION "Modbus address of the product"
                ::= { atsMetroLegacyEntry 1 }

atsMetroLegacyProductIndex    OBJECT-TYPE
                SYNTAX      Unsigned32(1..33)  -- 32 Products + 1 Gateway
                MAX-ACCESS  read-only
                STATUS      current
                DESCRIPTION "Index of the Product to reach (1 = Gateway itself)"
                ::= { atsMetroLegacyEntry 5 }

atsMetroLegacyRowStatus      OBJECT-TYPE
                SYNTAX       RowStatus
                MAX-ACCESS   read-create
                STATUS       current
                DESCRIPTION "The status of this conceptual row."
                ::= { atsMetroLegacyEntry 10 }

atsMetroLegacyVoltPhPhU12Source1   OBJECT-TYPE
                SYNTAX      Unsigned32
                MAX-ACCESS  read-only
                STATUS      current
                DESCRIPTION "Ph-Ph Voltage U12 of Source 1 (1/100 V)"
                ::= { atsMetroLegacyEntry 135079 }  
                
atsMetroLegacyVoltPhPhU23Source1   OBJECT-TYPE
                SYNTAX      Unsigned32
                MAX-ACCESS  read-only
                STATUS      current
                DESCRIPTION "Ph-Ph Voltage U23 of Source 1 (1/100 V)"
                ::= { atsMetroLegacyEntry 135080 }  
                
atsMetroLegacyVoltPhPhU31Source1   OBJECT-TYPE
                SYNTAX      Unsigned32
                MAX-ACCESS  read-only
                STATUS      current
                DESCRIPTION "Ph-Ph Voltage U31 of Source 1 (1/100 V)"
                ::= { atsMetroLegacyEntry 135081 }  
                
atsMetroLegacyVoltPhNV1Source1   OBJECT-TYPE
                SYNTAX      Unsigned32
                MAX-ACCESS  read-only
                STATUS      current
                DESCRIPTION "Ph-N Voltage V1 of Source 1 (1/100 V)"
                ::= { atsMetroLegacyEntry 135082 }
                
atsMetroLegacyVoltPhNV2Source1   OBJECT-TYPE
                SYNTAX      Unsigned32
                MAX-ACCESS  read-only
                STATUS      current
                DESCRIPTION "Ph-N Voltage V2 of Source 1 (1/100 V)"
                ::= { atsMetroLegacyEntry 135083 }
                
atsMetroLegacyVoltPhNV3Source1   OBJECT-TYPE
                SYNTAX      Unsigned32
                MAX-ACCESS  read-only
                STATUS      current
                DESCRIPTION "Ph-N Voltage V3 of Source 1 (1/100 V)"
                ::= { atsMetroLegacyEntry 135084 }
                
atsMetroLegacyFrequencySource1   OBJECT-TYPE
                SYNTAX      Unsigned32
                MAX-ACCESS  read-only
                STATUS      current
                DESCRIPTION "Frequency of Source 1 (mHz)"
                ::= { atsMetroLegacyEntry 135085 }

atsMetroLegacyVoltPhPhU12Source2   OBJECT-TYPE
                SYNTAX      Unsigned32
                MAX-ACCESS  read-only
                STATUS      current
                DESCRIPTION "Ph-Ph Voltage U12 of Source 2 (1/100 V)"
                ::= { atsMetroLegacyEntry 135086 }  
                
atsMetroLegacyVoltPhPhU23Source2   OBJECT-TYPE
                SYNTAX      Unsigned32
                MAX-ACCESS  read-only
                STATUS      current
                DESCRIPTION "Ph-Ph Voltage U23 of Source 2 (1/100 V)"
                ::= { atsMetroLegacyEntry 135087 }  
                
atsMetroLegacyVoltPhPhU31Source2   OBJECT-TYPE
                SYNTAX      Unsigned32
                MAX-ACCESS  read-only
                STATUS      current
                DESCRIPTION "Ph-Ph Voltage U31 of Source 2 (1/100 V)"
                ::= { atsMetroLegacyEntry 135088 }  
                
atsMetroLegacyVoltPhNV1Source2   OBJECT-TYPE
                SYNTAX      Unsigned32
                MAX-ACCESS  read-only
                STATUS      current
                DESCRIPTION "Ph-N Voltage V1 of Source 2 (1/100 V)"
                ::= { atsMetroLegacyEntry 135089 }
                
atsMetroLegacyVoltPhNV2Source2   OBJECT-TYPE
                SYNTAX      Unsigned32
                MAX-ACCESS  read-only
                STATUS      current
                DESCRIPTION "Ph-N Voltage V2 of Source 2 (1/100 V)"
                ::= { atsMetroLegacyEntry 135090 }
                
atsMetroLegacyVoltPhNV3Source2   OBJECT-TYPE
                SYNTAX      Unsigned32
                MAX-ACCESS  read-only
                STATUS      current
                DESCRIPTION "Ph-N Voltage V3 of Source 2 (1/100 V)"
                ::= { atsMetroLegacyEntry 135091 }
                
atsMetroLegacyFrequencySource2   OBJECT-TYPE
                SYNTAX      Unsigned32
                MAX-ACCESS  read-only
                STATUS      current
                DESCRIPTION "Frequency of Source 2 (mHz)"
                ::= { atsMetroLegacyEntry 135092 }
         
-- *******************************************************************************
-- ********************* ATS METRO TABLE *****************************************
atsMetroTable   OBJECT-TYPE
                SYNTAX      SEQUENCE OF SeqAtsMetroEnt
                MAX-ACCESS  not-accessible
                STATUS      current
                DESCRIPTION "Ats Metrology Table"
                ::= { productAts 11 }

atsMetroEntry   OBJECT-TYPE
                SYNTAX      SeqAtsMetroEnt
                MAX-ACCESS  not-accessible
                STATUS      current
                DESCRIPTION "Ats Metrology Details for given Product Index"
                INDEX  { atsMetroModbusAddress, atsMetroSourceIndex }
                ::= { atsMetroTable 1 }

atsMetroModbusAddress    OBJECT-TYPE
                SYNTAX      Unsigned32(1..255)
                MAX-ACCESS  read-only
                STATUS      current
                DESCRIPTION "Modbus address of the product"
                ::= { atsMetroEntry 1 }

atsMetroProductIndex    OBJECT-TYPE
                SYNTAX      Unsigned32(1..33)  -- 32 Products + 1 Gateway
                MAX-ACCESS  read-only
                STATUS      current
                DESCRIPTION "Index of the Product to reach (1 = Gateway itself)"
                ::= { atsMetroEntry 5 }
				
atsMetroSourceIndex       OBJECT-TYPE
                SYNTAX      Unsigned32 (1..16)  -- multiplie sources
                MAX-ACCESS  read-only
                STATUS      current
                DESCRIPTION "Index of the Source to reach"
                ::= { atsMetroEntry 6 }

atsMetroRowStatus      OBJECT-TYPE
                SYNTAX       RowStatus
                MAX-ACCESS   read-create
                STATUS       current
                DESCRIPTION "The status of this conceptual row."
                ::= { atsMetroEntry 10 }

atsMetroVoltPhPhU12Source   OBJECT-TYPE
                SYNTAX      Unsigned32
                MAX-ACCESS  read-only
                STATUS      current
                DESCRIPTION "Ph-Ph Voltage U12 of Source (1/100 V)"
                ::= { atsMetroEntry 110233 }  
                
atsMetroVoltPhPhU23Source   OBJECT-TYPE
                SYNTAX      Unsigned32
                MAX-ACCESS  read-only
                STATUS      current
                DESCRIPTION "Ph-Ph Voltage U23 of Source (1/100 V)"
                ::= { atsMetroEntry 110234 }  

atsMetroVoltPhPhU31Source   OBJECT-TYPE
                SYNTAX      Unsigned32
                MAX-ACCESS  read-only
                STATUS      current
                DESCRIPTION "Ph-Ph Voltage U31 of Source (1/100 V)"
                ::= { atsMetroEntry 110235 }  
                
atsMetroVoltPhNV1Source   OBJECT-TYPE
                SYNTAX      Unsigned32
                MAX-ACCESS  read-only
                STATUS      current
                DESCRIPTION "Ph-N Voltage V1 of Source (1/100 V)"
                ::= { atsMetroEntry 110228 }
                
atsMetroVoltPhNV2Source   OBJECT-TYPE
                SYNTAX      Unsigned32
                MAX-ACCESS  read-only
                STATUS      current
                DESCRIPTION "Ph-N Voltage V2 of Source (1/100 V)"
                ::= { atsMetroEntry 110229 }
                
atsMetroVoltPhNV3Source   OBJECT-TYPE
                SYNTAX      Unsigned32
                MAX-ACCESS  read-only
                STATUS      current
                DESCRIPTION "Ph-N Voltage V3 of Source (1/100 V)"
                ::= { atsMetroEntry 110230 }
                
atsMetroFrequencySource   OBJECT-TYPE
                SYNTAX      Unsigned32
                MAX-ACCESS  read-only
                STATUS      current
                DESCRIPTION "Frequency of Source (mHz)"
                ::= { atsMetroEntry 40014 }


                
-- *******************************************************************************
-- ********************* ATS STATUS TABLE ****************************************
atsStatusTable       OBJECT-TYPE
                SYNTAX      SEQUENCE OF SeqAtsStatusEnt
                MAX-ACCESS  not-accessible
                STATUS      current
                DESCRIPTION "Ats Status Table"
                ::= { productAts 50 }

atsStatusEntry       OBJECT-TYPE
                SYNTAX      SeqAtsStatusEnt
                MAX-ACCESS  not-accessible
                STATUS      current
                DESCRIPTION "Ats Status Details for given Product Index"
                INDEX  { atsStatusModbusAddress  }
                ::= { atsStatusTable 1 }

atsStatusModbusAddress    OBJECT-TYPE
                SYNTAX      Unsigned32(1..255)
                MAX-ACCESS  read-only
                STATUS      current
                DESCRIPTION "Modbus address of the product"
                ::= { atsStatusEntry 1 }

atsStatusProductIndex    OBJECT-TYPE
                SYNTAX      Unsigned32(1..33)  -- 32 Products + 1 Gateway
                MAX-ACCESS  read-only
                STATUS      current
                DESCRIPTION "Index of the Product to reach (1 = Gateway itself)"
                ::= { atsStatusEntry 5 }

atsStatusRowStatus      OBJECT-TYPE
                SYNTAX       RowStatus
                MAX-ACCESS   read-create
                STATUS       current
                DESCRIPTION "The status of this conceptual row."
                ::= { atsStatusEntry 10 }

atsStatusSourcePrio   OBJECT-TYPE
                SYNTAX      SocomecAtsSourcePrio
                MAX-ACCESS  read-only
                STATUS      current
                DESCRIPTION "ATS Source priority"
                ::= { atsStatusEntry 135000 }
                
atsStatusSwitchAlarmFaultCode   OBJECT-TYPE
                SYNTAX      SocomecAtsAlarmFault
                MAX-ACCESS  read-only
                STATUS      current
                DESCRIPTION "ATS Alarm fault code"
                ::= { atsStatusEntry 135001 }
                
atsStatusSwitchOperatingMode   OBJECT-TYPE
                SYNTAX      SocomecAtsOperatingMode
                MAX-ACCESS  read-only
                STATUS      current
                DESCRIPTION "ATS Operating Mode: 0 = Manual, 1 = Locked, 16 = Auto, 32 = Remote, 64 = Inhibit"
                ::= { atsStatusEntry 135038 }
                
atsStatusSwitchPosition   OBJECT-TYPE
                SYNTAX      SocomecAtsPosition
                MAX-ACCESS  read-only
                STATUS      current
                DESCRIPTION "ATS Switch Position: 0 = Unknown, 1 = Position 0, 2 = Position 1, 3 = Position 2"
                ::= { atsStatusEntry 135039 }
                
atsStatusRelayStateSource1   OBJECT-TYPE
                SYNTAX      Unsigned32
                MAX-ACCESS  read-only
                STATUS      current
                DESCRIPTION "ATS Generator relay State Source 1: 0 = Inactive, 1 = Active"
                ::= { atsStatusEntry 135041 }
                
atsStatusRelayStateSource2   OBJECT-TYPE
                SYNTAX      Unsigned32
                MAX-ACCESS  read-only
                STATUS      current
                DESCRIPTION "ATS Generator relay State Source 2: 0 = Inactive, 1 = Active"
                ::= { atsStatusEntry 135042 }
                
atsStatusSwitchStateSource1   OBJECT-TYPE
                SYNTAX      SocomecAtsStateSource
                MAX-ACCESS  read-only
                STATUS      current
                DESCRIPTION "ATS State of Source 1"
                ::= { atsStatusEntry 135044 }
                
atsStatusSwitchStateSource2   OBJECT-TYPE
                SYNTAX      SocomecAtsStateSource
                MAX-ACCESS  read-only
                STATUS      current
                DESCRIPTION "ATS State of Source 2"
                ::= { atsStatusEntry 135045 }
                
atsStatusSwitchTestInProgress   OBJECT-TYPE
                SYNTAX      SocomecAtsTestInProgress
                MAX-ACCESS  read-only
                STATUS      current
                DESCRIPTION "ATS Test in progress status"
                ::= { atsStatusEntry 135046 }
                
atsStatusCycleCounter   OBJECT-TYPE
                SYNTAX      Unsigned32
                MAX-ACCESS  read-only
                STATUS      current
                DESCRIPTION "ATS "
                ::= { atsStatusEntry 135048 }
                
atsStatusOperationCounterPos1   OBJECT-TYPE
                SYNTAX      Unsigned32
                MAX-ACCESS  read-only
                STATUS      current
                DESCRIPTION "ATS Position 2 counter"
                ::= { atsStatusEntry 135049 }
                
atsStatusOperationCounterPos2   OBJECT-TYPE
                SYNTAX      Unsigned32
                MAX-ACCESS  read-only
                STATUS      current
                DESCRIPTION "ATS Position 2 counter"
                ::= { atsStatusEntry 135050 }
                
atsStatusSwitchFaultSummary   OBJECT-TYPE
                SYNTAX      SocomecAtsSwitchFaultSummary
                MAX-ACCESS  read-only
                STATUS      current
                DESCRIPTION "ATS Fault summary"
                ::= { atsStatusEntry 135052 }
                
atsStatusSwitchLastCause   OBJECT-TYPE
                SYNTAX      SocomecAtsSwitchLastCause
                MAX-ACCESS  read-only
                STATUS      current
                DESCRIPTION "ATS last switch-over cause"
                ::= { atsStatusEntry 135053 }

		 
-- *******************************************************************************
-- ********************* ATS METRO TABLE (LEGAY TABLE) ***************************
commandTable   OBJECT-TYPE
                SYNTAX      SEQUENCE OF SeqProductCommandEnt
                MAX-ACCESS  not-accessible
                STATUS      current
                DESCRIPTION "Product Command Table"
                ::= { productCommand 10 }

commandEntry   OBJECT-TYPE
                SYNTAX      SeqProductCommandEnt
                MAX-ACCESS  not-accessible
                STATUS      current
                DESCRIPTION "Command Entry for given Product Index"
                INDEX  { commandModbusAddress, commandLineIndex }
                ::= { commandTable 1 }

commandModbusAddress    OBJECT-TYPE
                SYNTAX      Unsigned32(1..255)
                MAX-ACCESS  read-only
                STATUS      current
                DESCRIPTION "Modbus address of the product to command"
                ::= { commandEntry 1 }

commandProductIndex    OBJECT-TYPE
                SYNTAX      Unsigned32(1..33)  -- 32 Products + 1 Gateway
                MAX-ACCESS  read-only
                STATUS      current
                DESCRIPTION "Index of the Product to reach (1 = Gateway itself)"
                ::= { commandEntry 5 }

commandLineIndex       OBJECT-TYPE
                SYNTAX      Unsigned32
                MAX-ACCESS  read-only
                STATUS      current
                DESCRIPTION "Index of the Line to reach"
                ::= { commandEntry 6 }

commandRowStatus      OBJECT-TYPE
                SYNTAX       RowStatus
                MAX-ACCESS   read-create
                STATUS       current
                DESCRIPTION "The status of this conceptual row."
                ::= { commandEntry 10 }

commandAtsGensetStartOrder   OBJECT-TYPE
                SYNTAX      Unsigned32
                MAX-ACCESS  read-write
                STATUS      current
                DESCRIPTION "Command for Genset start order. 0 = GS1 start, 1 = GS1 stop, 2 = GS2 start, 3 = GS2 stop"
                ::= { commandEntry 156039 }

commandAtsPosition   OBJECT-TYPE
                SYNTAX      Unsigned32
                MAX-ACCESS  read-write
                STATUS      current
                DESCRIPTION "Command to set Ats Position. 1	= Position in Zero, 2 = Position in 1, 3 = Position in 2"
                ::= { commandEntry 156018 }

commandAtsPriorityMode   OBJECT-TYPE
                SYNTAX      Unsigned32
                MAX-ACCESS  read-write
                STATUS      current
                DESCRIPTION "Command to set Ats Priority Mode. 0 = Network, 1 = Source 1, 2 = Source 2"
                ::= { commandEntry 156017 }

commandAtsOperatingMode   OBJECT-TYPE
                SYNTAX      Unsigned32
                MAX-ACCESS  read-write
                STATUS      current
                DESCRIPTION "Command to set Ats Operating Mode. 3 = Auto, 4 = Inhibit, 5 = Remote Control"
                ::= { commandEntry 156016 }

commandAtsCommandAlarm   OBJECT-TYPE
                SYNTAX      Unsigned32
                MAX-ACCESS  read-write
                STATUS      current
                DESCRIPTION "Command for Ats Alarm. 1 = Set RTE (By Keyboard), 2 = Clear TOF (By Keyboard), 3 = Set TOF (By Keyboard), 4 = Set TON (By Keyboard),
							5 = Set EOF (By input), 6 = Set EON (By input), 7 = Clear EOF (By input), 8 = Clear EON (By input), 10 = Clear TON (By Keyboard),
							16 = Clear Alarms/Faults (By input), 21 = Set EST Reset (By keyboard)"
                ::= { commandEntry 156015 }
				
-- *******************************************************************************
-- ********************* TRAPS DEFINITION ****************************************
analogAlarms NOTIFICATION-TYPE
    STATUS       current
    DESCRIPTION  "Analogical Alarm"
    ::= { productTraps 10 }
logicalAlarms NOTIFICATION-TYPE
    STATUS       current
    DESCRIPTION  "Logical Alarm"
    ::= { productTraps 20 }
combinationAlarms NOTIFICATION-TYPE
    STATUS       current
    DESCRIPTION  "Combination Alarm"
    ::= { productTraps 30 }
inrushAlarms NOTIFICATION-TYPE
    STATUS       current
    DESCRIPTION  "In Rush Alarm"
    ::= { productTraps 40 }
eventsAlarms NOTIFICATION-TYPE
    STATUS       current
    DESCRIPTION  "Event EN50160 Alarm"
    ::= { productTraps 50 }
systemAlarms NOTIFICATION-TYPE
    STATUS       current
    DESCRIPTION  "System Alarm"
    ::= { productTraps 60 }
protectionAlarms NOTIFICATION-TYPE
    STATUS       current
    DESCRIPTION  "Protection Alarm"
    ::= { productTraps 70 }
faultAlarms NOTIFICATION-TYPE
    STATUS       current
    DESCRIPTION  "Fault Alarm"
    ::= { productTraps 80 }
rcmAlarms NOTIFICATION-TYPE
    STATUS       current
    DESCRIPTION  "Rcm Alarm"
    ::= { productTraps 90 }
comparisonAlarms NOTIFICATION-TYPE
    STATUS       current
    DESCRIPTION  "Comparison Alarm"
    ::= { productTraps 100 }
unknownAlarms NOTIFICATION-TYPE
    STATUS       current
    DESCRIPTION  "Unknown Alarm"
    ::= { productTraps 250 }

-- Conformance information ******************************************
socomecIdentificationMIBCompliances         OBJECT IDENTIFIER ::= {socomecMIBConformance 1010}
socomecIdentificationMIBGroups              OBJECT IDENTIFIER ::= {socomecMIBConformance 1011}
socomecCircuitMIBCompliances                OBJECT IDENTIFIER ::= {socomecMIBConformance 1020}
socomecCircuitMIBGroups                     OBJECT IDENTIFIER ::= {socomecMIBConformance 1021}
socomecLoadCurvesMIBCompliances             OBJECT IDENTIFIER ::= {socomecMIBConformance 2010}
socomecLoadCurvesMIBGroups                  OBJECT IDENTIFIER ::= {socomecMIBConformance 2011}
socomecEnergyMIBCompliances                 OBJECT IDENTIFIER ::= {socomecMIBConformance 2012}
socomecEnergyMIBGroups                      OBJECT IDENTIFIER ::= {socomecMIBConformance 2013}
socomecMultifluidMIBCompliances             OBJECT IDENTIFIER ::= {socomecMIBConformance 2014}
socomecMultifluidMIBGroups                  OBJECT IDENTIFIER ::= {socomecMIBConformance 2015}
socomecInstantaneousMIBCompliances          OBJECT IDENTIFIER ::= {socomecMIBConformance 2020}
socomecInstantaneousMIBGroups               OBJECT IDENTIFIER ::= {socomecMIBConformance 2021}
socomecAveragesMIBCompliances               OBJECT IDENTIFIER ::= {socomecMIBConformance 2030}
socomecAveragesMIBGroups                    OBJECT IDENTIFIER ::= {socomecMIBConformance 2031}
socomecMaxInstantaneousMIBCompliances       OBJECT IDENTIFIER ::= {socomecMIBConformance 2040}
socomecMaxInstantaneousMIBGroups            OBJECT IDENTIFIER ::= {socomecMIBConformance 2041}
socomecMinInstantaneousMIBCompliances       OBJECT IDENTIFIER ::= {socomecMIBConformance 2050}
socomecMinInstantaneousMIBGroups            OBJECT IDENTIFIER ::= {socomecMIBConformance 2051}
socomecMaxAveragesMIBCompliances            OBJECT IDENTIFIER ::= {socomecMIBConformance 2060}
socomecMaxAveragesMIBGroups                 OBJECT IDENTIFIER ::= {socomecMIBConformance 2061}
socomecMinAveragesMIBCompliances            OBJECT IDENTIFIER ::= {socomecMIBConformance 2070}
socomecMinAveragesMIBGroups                 OBJECT IDENTIFIER ::= {socomecMIBConformance 2071}
socomecInstantaneousQualityMIBCompliances   OBJECT IDENTIFIER ::= {socomecMIBConformance 2080}
socomecInstantaneousQualityMIBGroups        OBJECT IDENTIFIER ::= {socomecMIBConformance 2081}
socomecMetroDCMIBCompliances                OBJECT IDENTIFIER ::= {socomecMIBConformance 2090}
socomecMetroDCMIBGroups                     OBJECT IDENTIFIER ::= {socomecMIBConformance 2091}
socomecAtsMIBCompliances                    OBJECT IDENTIFIER ::= {socomecMIBConformance 4000}
socomecAtsMIBGroups                         OBJECT IDENTIFIER ::= {socomecMIBConformance 4001}
socomecCommandMIBCompliances                OBJECT IDENTIFIER ::= {socomecMIBConformance 8000}
socomecCommandMIBGroups                     OBJECT IDENTIFIER ::= {socomecMIBConformance 8001}	
socomecTrapsMIBCompliances                  OBJECT IDENTIFIER ::= {socomecMIBConformance 9000}
socomecTrapsMIBGroups                       OBJECT IDENTIFIER ::= {socomecMIBConformance 9001}

-- Compliance statements
socomecIdentificationMIBCompliance MODULE-COMPLIANCE
    STATUS       current
    DESCRIPTION "The compliance statement for Socomec Identification table."
    MODULE    -- this module
    MANDATORY-GROUPS { socomecIdentificationGroup }
    ::= { socomecIdentificationMIBCompliances 1 }

socomecIdentificationGroup OBJECT-GROUP
    OBJECTS {                
				   identType,
                   identSWVersion,
                   identVersionBuildDate,
                   identSerialAASS,
                   identSerialSSTL,
                   identSerialOrder,
                   identSerialReserve,
                   identOperatingCounter
            }
    STATUS       current
    DESCRIPTION "Collection of Socomec identification objects"
    ::= { socomecIdentificationMIBGroups 1 }

socomecCircuitMIBCompliance MODULE-COMPLIANCE
    STATUS       current
    DESCRIPTION "The compliance statement for Socomec Circuit table."
    MODULE    -- this module
    MANDATORY-GROUPS { socomecCircuitGroup }
    ::= { socomecCircuitMIBCompliances 1 }

socomecCircuitGroup OBJECT-GROUP
    OBJECTS {
                   circuitProductIndex
                   circuitProductLine
				   circuitProductModbusAddress
                   circuitName
                   circuitType
                   circuitUsage
                   circuitNature
                   circuitLocation
            }
    STATUS       current
    DESCRIPTION "Collection of Socomec Circuit objects"
    ::= { socomecCircuitMIBGroups 1 }

socomecLoadCurvesMIBCompliance MODULE-COMPLIANCE
    STATUS       current
    DESCRIPTION "The compliance statement for Socomec Load Curves Metrology table."
    MODULE    -- this module
    MANDATORY-GROUPS { socomecLoadCurvesGroup }
    ::= { socomecLoadCurvesMIBCompliances 1 }

socomecLoadCurvesGroup OBJECT-GROUP
    OBJECTS {
                   loadCurvesActivePowerPos,
                   loadCurvesActivePowerNeg,
                   loadCurvesReactivePowerPos,
                   loadCurvesReactivePowerNeg,
                   loadCurvesApparentPower
            }
    STATUS       current
    DESCRIPTION "Collection of Socomec Metrology Load Curve objects"
    ::= { socomecLoadCurvesMIBGroups 1 }

socomecEnergyMIBCompliance MODULE-COMPLIANCE
    STATUS       current
    DESCRIPTION "The compliance statement for Socomec Energies Metrology table."
    MODULE    -- this module
    MANDATORY-GROUPS { socomecenergyGroup }
    ::= { socomecEnergyMIBCompliances 1 }

socomecenergyGroup OBJECT-GROUP
    OBJECTS {
                   engTotalHourMeter                        ,
                   engTotalEnergyActivePos                  ,
                   engTotalEnergyActiveResidualPos          ,
                   engTotalEnergyActiveNeg                  ,
                   engTotalEnergyActiveResidualNeg          ,
                   engTotalEnergyReactivePos                ,
                   engTotalEnergyReactiveResidualPos        ,
                   engTotalEnergyReactiveNeg                ,
                   engTotalEnergyReactiveResidualNeg        ,
                   engTotalEnergyApparent                   ,
                   engTotalEnergyApparentResidual           ,
                   engTotalEnergyReactiveLaggingPos         ,
                   engTotalEnergyReactiveLaggingResidualPos ,
                   engTotalEnergyReactiveLaggingNeg         ,
                   engTotalEnergyReactiveLaggingResidualNeg ,
                   engTotalEnergyReactiveLeadingPos         ,
                   engTotalEnergyReactiveLeadingResidualPos ,
                   engTotalEnergyReactiveLeadingNeg         ,
                   engTotalEnergyReactiveLeadingResidualNeg ,
                   engPartialHourMeter                      ,
                   engPartialEnergyActivePos                ,
                   engPartialEnergyActiveResidualPos        ,
                   engPartialEnergyActiveNeg                ,
                   engPartialEnergyActiveResidualNeg        ,
                   engPartialEnergyReactivePos              ,
                   engPartialEnergyReactiveResidualPos      ,
                   engPartialEnergyReactiveNeg              ,
                   engPartialEnergyReactiveResidualNeg      ,
                   engPartialEnergyApparent                 ,
                   engPartialEnergyApparentResidual         ,
                   engLastPartialResetDate                  ,
                   --engLastPartialHourMeter                ,
                   engLastPartialEnergyActivePos            ,
                   engLastPartialEnergyActiveResidualPos    ,
                   engLastPartialEnergyActiveNeg            ,
                   engLastPartialEnergyActiveResidualNeg    ,
                   engLastPartialEnergyReactivePos          ,
                   engLastPartialEnergyReactiveResidualPos  ,
                   engLastPartialEnergyReactiveNeg          ,
                   engLastPartialEnergyReactiveResidualNeg  ,
                   engLastPartialEnergyApparent             ,
                   engLastPartialEnergyApparentResidual     
            }
    STATUS       current
    DESCRIPTION "Collection of Socomec Metrology Energy objects"
    ::= { socomecEnergyMIBGroups 1 }

socomecMultifluidMIBCompliance MODULE-COMPLIANCE
    STATUS       current
    DESCRIPTION "The compliance statement for Socomec MultiFluids Metrology table."
    MODULE    -- this module
    MANDATORY-GROUPS { socomecMultifluidGroup }
    ::= { socomecMultifluidMIBCompliances 1 }

socomecMultifluidGroup OBJECT-GROUP
    OBJECTS {
                   mffTotalMeter                    ,
                   mffPartialMeter                  ,
                   mffUnit                          ,
                   mffWeight
            }
    STATUS       current
    DESCRIPTION "Collection of Socomec Metrology Multifluid objects"
    ::= { socomecMultifluidMIBGroups 1 }

socomecInstantaneousMIBCompliance MODULE-COMPLIANCE
    STATUS       current
    DESCRIPTION "The compliance statement for Socomec instantaneous metrology table."
    MODULE    -- this module
    MANDATORY-GROUPS { socomecInstantaneousGroup }
    ::= { socomecInstantaneousMIBCompliances 1 }

socomecInstantaneousGroup OBJECT-GROUP
    OBJECTS {
                   instVoltSystPhN,
                   instVoltSystPhPh,
                   instCurrentSyst,
                   instFrequency,
                   instVoltPhNV1,
                   instVoltPhNV2,
                   instVoltPhNV3,
                   instVoltPhNVn,
                   instVoltPhPhU12,
                   instVoltPhPhU23,
                   instVoltPhPhU31,
                   instCurrentI1,
                   instCurrentI2,
                   instCurrentI3,
                   instCurrentIn,
                   instCurrentInba,
                   instCurrentIdir,
                   instCurrentIinv,
                   instCurrentIhom,
                   instCurrentInb,
                   instPowerApparentNom,
                   instTotalPowerActive,
                   instTotalPowerReactive,
                   instTotalPowerApparent,
                   instTotalPowerFactor,
                   instTotalPowerFactorType,
                   instPowerActiveP1,
                   instPowerActiveP2,
                   instPowerActiveP3,
                   instPowerReactiveQ1,
                   instPowerReactiveQ2,
                   instPowerReactiveQ3,
                   instPowerApparentS1,
                   instPowerApparentS2,
                   instPowerApparentS3,
                   instPowerFactorPF1,
                   instPowerFactorTypeSPF1,
                   instPowerFactorPF2,
                   instPowerFactorTypeSPF2,
                   instPowerFactorPF3,
                   instPowerFactorTypeSPF3
            }
    STATUS       current
    DESCRIPTION "Collection of Socomec instantaneous metrology objects"
    ::= { socomecInstantaneousMIBGroups 1 }

socomecAveragesMIBCompliance MODULE-COMPLIANCE
    STATUS       current
    DESCRIPTION "The compliance statement for Socomec Averages metrology table."
    MODULE    -- this module
    MANDATORY-GROUPS { socomecAveragesGroup }
    ::= { socomecAveragesMIBCompliances 1 }

socomecAveragesGroup OBJECT-GROUP
    OBJECTS {
				   avgDateLastInstance,
                   avgVoltSystPhN,
                   avgVoltSystPhPh,
                   avgCurrentSyst,
                   avgFrequency,
                   avgVoltPhNV1,
                   avgVoltPhNV2,
                   avgVoltPhNV3,
                   avgVoltPhNVn,
                   avgVoltPhPhU12,
                   avgVoltPhPhU23,
                   avgVoltPhPhU31,
                   avgCurrentI1,
                   avgCurrentI2,
                   avgCurrentI3,
                   avgCurrentIn,
                   avgCurrentInba,
                   avgCurrentIdir,
                   avgCurrentIinv,
                   avgCurrentIhom,
                   avgCurrentInb,
                   avgTotalPowerActive,
                   avgTotalPowerReactive,
                   avgTotalPowerApparent,
                   avgTotalPowerFactor,
                   avgTotalPowerFactorType,
                   avgPowerActiveP1,
                   avgPowerActiveP2,
                   avgPowerActiveP3,
                   avgPowerReactiveQ1,
                   avgPowerReactiveQ2,
                   avgPowerReactiveQ3,
                   avgPowerApparentS1,
                   avgPowerApparentS2,
                   avgPowerApparentS3,
                   avgPowerFactorPF1,
                   avgPowerFactorTypeSPF1,
                   avgPowerFactorPF2,
                   avgPowerFactorTypeSPF2,
                   avgPowerFactorPF3,
                   avgPowerFactorTypeSPF3
            }
    STATUS       current
    DESCRIPTION "Collection of Socomec average metrology objects"
    ::= { socomecAveragesMIBGroups 1 }

socomecMaxInstantaneousMIBCompliance MODULE-COMPLIANCE
    STATUS       current
    DESCRIPTION "The compliance statement for Socomec Max Instantaneous Metrology table."
    MODULE    -- this module
    MANDATORY-GROUPS { socomecMaxInstantaneousGroup }
    ::= { socomecMaxInstantaneousMIBCompliances 1 }

socomecMaxInstantaneousGroup OBJECT-GROUP
    OBJECTS {
                   maxInstFrequency,
                   maxInstFrequencyDate,
                   maxInstVoltPhNV1,
                   maxInstVoltPhNV1Date,
                   maxInstVoltPhNV2,
                   maxInstVoltPhNV2Date,
                   maxInstVoltPhNV3,
                   maxInstVoltPhNV3Date,
                   maxInstVoltPhNVn,
                   maxInstVoltPhNVnDate,
                   maxInstVoltPhPhU12,
                   maxInstVoltPhPhU12Date,
                   maxInstVoltPhPhU23,
                   maxInstVoltPhPhU23Date,
                   maxInstVoltPhPhU31,
                   maxInstVoltPhPhU31Date,
                   maxInstCurrentI1,
                   maxInstCurrentI1Date,
                   maxInstCurrentI2,
                   maxInstCurrentI2Date,
                   maxInstCurrentI3,
                   maxInstCurrentI3Date,
                   maxInstCurrentIn,
                   maxInstCurrentInDate,
                   maxInstTotalPowerActive,
                   maxInstTotalPowerActiveDate,
                   maxInstTotalPowerReactive,
                   maxInstTotalPowerReactiveDate,
                   maxInstTotalPowerApparent,
                   maxInstTotalPowerApparentDate,
                   maxInstTotalPowerFactor,
                   maxInstTotalPowerFactorType,
                   maxInstTotalPowerFactorDate,
                   maxInstPowerActiveP1,
                   maxInstPowerActiveP1Date,
                   maxInstPowerActiveP2,
                   maxInstPowerActiveP2Date,
                   maxInstPowerActiveP3,
                   maxInstPowerActiveP3Date,
                   maxInstPowerReactiveQ1,
                   maxInstPowerReactiveQ1Date,
                   maxInstPowerReactiveQ2,
                   maxInstPowerReactiveQ2Date,
                   maxInstPowerReactiveQ3,
                   maxInstPowerReactiveQ3Date,
                   maxInstPowerApparentS1,
                   maxInstPowerApparentS1Date,
                   maxInstPowerApparentS2,
                   maxInstPowerApparentS2Date,
                   maxInstPowerApparentS3,
                   maxInstPowerApparentS3Date,
                   maxInstPowerFactorPF1,
                   maxInstPowerFactorTypeSPF1,
                   maxInstPowerFactorPF1Date,
                   maxInstPowerFactorPF2,
                   maxInstPowerFactorTypeSPF2,
                   maxInstPowerFactorPF2Date,
                   maxInstPowerFactorPF3,
                   maxInstPowerFactorTypeSPF3,
                   maxInstPowerFactorPF3Date
            }
    STATUS       current
    DESCRIPTION "Collection of Socomec Max Instantaneous metrology objects"
    ::= { socomecMaxInstantaneousMIBGroups 1 }

socomecMinInstantaneousMIBCompliance MODULE-COMPLIANCE
    STATUS       current
    DESCRIPTION "The compliance statement for Socomec Min Instantaneous Metrology table."
    MODULE    -- this module
    MANDATORY-GROUPS { socomecMinInstantaneousGroup }
    ::= { socomecMinInstantaneousMIBCompliances 1 }

socomecMinInstantaneousGroup OBJECT-GROUP
    OBJECTS {
                   minInstFrequency,
                   minInstFrequencyDate,
                   minInstVoltPhNV1,
                   minInstVoltPhNV1Date,
                   minInstVoltPhNV2,
                   minInstVoltPhNV2Date,
                   minInstVoltPhNV3,
                   minInstVoltPhNV3Date,
                   minInstVoltPhNVn,
                   minInstVoltPhNVnDate,
                   minInstVoltPhPhU12,
                   minInstVoltPhPhU12Date,
                   minInstVoltPhPhU23,
                   minInstVoltPhPhU23Date,
                   minInstVoltPhPhU31,
                   minInstVoltPhPhU31Date,
                   minInstCurrentI1,
                   minInstCurrentI1Date,
                   minInstCurrentI2,
                   minInstCurrentI2Date,
                   minInstCurrentI3,
                   minInstCurrentI3Date,
                   minInstCurrentIn,
                   minInstCurrentInDate,
                   minInstTotalPowerActive,
                   minInstTotalPowerActiveDate,
                   minInstTotalPowerReactive,
                   minInstTotalPowerReactiveDate,
                   minInstTotalPowerApparent,
                   minInstTotalPowerApparentDate,
                   minInstTotalPowerFactor,
                   minInstTotalPowerFactorType,
                   minInstTotalPowerFactorDate,
                   minInstPowerActiveP1,
                   minInstPowerActiveP1Date,
                   minInstPowerActiveP2,
                   minInstPowerActiveP2Date,
                   minInstPowerActiveP3,
                   minInstPowerActiveP3Date,
                   minInstPowerReactiveQ1,
                   minInstPowerReactiveQ1Date,
                   minInstPowerReactiveQ2,
                   minInstPowerReactiveQ2Date,
                   minInstPowerReactiveQ3,
                   minInstPowerReactiveQ3Date,
                   minInstPowerApparentS1,
                   minInstPowerApparentS1Date,
                   minInstPowerApparentS2,
                   minInstPowerApparentS2Date,
                   minInstPowerApparentS3,
                   minInstPowerApparentS3Date,
                   minInstPowerFactorPF1,
                   minInstPowerFactorTypeSPF1,
                   minInstPowerFactorPF1Date,
                   minInstPowerFactorPF2,
                   minInstPowerFactorTypeSPF2,
                   minInstPowerFactorPF2Date,
                   minInstPowerFactorPF3,
                   minInstPowerFactorTypeSPF3,
                   minInstPowerFactorPF3Date
            }
    STATUS       current
    DESCRIPTION "Collection of Socomec Min Instantaneous metrology objects"
    ::= { socomecMinInstantaneousMIBGroups 1 }

socomecMaxAveragesMIBCompliance MODULE-COMPLIANCE
    STATUS       current
    DESCRIPTION "The compliance statement for Socomec Max Averages Metrology table."
    MODULE    -- this module
    MANDATORY-GROUPS { socomecMaxAveragesGroup }
    ::= { socomecMaxAveragesMIBCompliances 1 }

socomecMaxAveragesGroup OBJECT-GROUP
    OBJECTS {
                   maxAvgFrequency,
                   maxAvgFrequencyDate,
                   maxAvgVoltPhNV1,
                   maxAvgVoltPhNV1Date,
                   maxAvgVoltPhNV2,
                   maxAvgVoltPhNV2Date,
                   maxAvgVoltPhNV3,
                   maxAvgVoltPhNV3Date,
                   maxAvgVoltPhNVn,
                   maxAvgVoltPhNVnDate,
                   maxAvgVoltPhPhU12,
                   maxAvgVoltPhPhU12Date,
                   maxAvgVoltPhPhU23,
                   maxAvgVoltPhPhU23Date,
                   maxAvgVoltPhPhU31,
                   maxAvgVoltPhPhU31Date,
                   maxAvgCurrentI1,
                   maxAvgCurrentI1Date,
                   maxAvgCurrentI2,
                   maxAvgCurrentI2Date,
                   maxAvgCurrentI3,
                   maxAvgCurrentI3Date,
                   maxAvgCurrentIn,
                   maxAvgCurrentInDate,
                   maxAvgTotalPowerActive,
                   maxAvgTotalPowerActiveDate,
                   maxAvgTotalPowerReactive,
                   maxAvgTotalPowerReactiveDate,
                   maxAvgTotalPowerApparent,
                   maxAvgTotalPowerApparentDate,
                   maxAvgTotalPowerFactor,
                   maxAvgTotalPowerFactorType,
                   maxAvgTotalPowerFactorDate,
                   maxAvgPowerActiveP1,
                   maxAvgPowerActiveP1Date,
                   maxAvgPowerActiveP2,
                   maxAvgPowerActiveP2Date,
                   maxAvgPowerActiveP3,
                   maxAvgPowerActiveP3Date,
                   maxAvgPowerReactiveQ1,
                   maxAvgPowerReactiveQ1Date,
                   maxAvgPowerReactiveQ2,
                   maxAvgPowerReactiveQ2Date,
                   maxAvgPowerReactiveQ3,
                   maxAvgPowerReactiveQ3Date,
                   maxAvgPowerApparentS1,
                   maxAvgPowerApparentS1Date,
                   maxAvgPowerApparentS2,
                   maxAvgPowerApparentS2Date,
                   maxAvgPowerApparentS3,
                   maxAvgPowerApparentS3Date,
                   maxAvgPowerFactorPF1,
                   maxAvgPowerFactorTypeSPF1,
                   maxAvgPowerFactorPF1Date,
                   maxAvgPowerFactorPF2,
                   maxAvgPowerFactorTypeSPF2,
                   maxAvgPowerFactorPF2Date,
                   maxAvgPowerFactorPF3,
                   maxAvgPowerFactorTypeSPF3,
                   maxAvgPowerFactorPF3Date
            }
    STATUS       current
    DESCRIPTION "Collection of Socomec Max Average metrology objects"
    ::= { socomecMaxAveragesMIBGroups 1 }

socomecMinAveragesMIBCompliance MODULE-COMPLIANCE
    STATUS       current
    DESCRIPTION "The compliance statement for Socomec Min Averages Metrology table."
    MODULE    -- this module
    MANDATORY-GROUPS { socomecMinAveragesGroup }
    ::= { socomecMinAveragesMIBCompliances 1 }

socomecMinAveragesGroup OBJECT-GROUP
    OBJECTS {
                   minAvgFrequency,
                   minAvgFrequencyDate,
                   minAvgVoltPhNV1,
                   minAvgVoltPhNV1Date,
                   minAvgVoltPhNV2,
                   minAvgVoltPhNV2Date,
                   minAvgVoltPhNV3,
                   minAvgVoltPhNV3Date,
                   minAvgVoltPhNVn,
                   minAvgVoltPhNVnDate,
                   minAvgVoltPhPhU12,
                   minAvgVoltPhPhU12Date,
                   minAvgVoltPhPhU23,
                   minAvgVoltPhPhU23Date,
                   minAvgVoltPhPhU31,
                   minAvgVoltPhPhU31Date,
                   minAvgCurrentI1,
                   minAvgCurrentI1Date,
                   minAvgCurrentI2,
                   minAvgCurrentI2Date,
                   minAvgCurrentI3,
                   minAvgCurrentI3Date,
                   minAvgCurrentIn,
                   minAvgCurrentInDate,
                   minAvgTotalPowerActive,
                   minAvgTotalPowerActiveDate,
                   minAvgTotalPowerReactive,
                   minAvgTotalPowerReactiveDate,
                   minAvgTotalPowerApparent,
                   minAvgTotalPowerApparentDate,
                   minAvgTotalPowerFactor,
                   minAvgTotalPowerFactorType,
                   minAvgTotalPowerFactorDate,
                   minAvgPowerActiveP1,
                   minAvgPowerActiveP1Date,
                   minAvgPowerActiveP2,
                   minAvgPowerActiveP2Date,
                   minAvgPowerActiveP3,
                   minAvgPowerActiveP3Date,
                   minAvgPowerReactiveQ1,
                   minAvgPowerReactiveQ1Date,
                   minAvgPowerReactiveQ2,
                   minAvgPowerReactiveQ2Date,
                   minAvgPowerReactiveQ3,
                   minAvgPowerReactiveQ3Date,
                   minAvgPowerApparentS1,
                   minAvgPowerApparentS1Date,
                   minAvgPowerApparentS2,
                   minAvgPowerApparentS2Date,
                   minAvgPowerApparentS3,
                   minAvgPowerApparentS3Date,
                   minAvgPowerFactorPF1,
                   minAvgPowerFactorTypeSPF1,
                   minAvgPowerFactorPF1Date,
                   minAvgPowerFactorPF2,
                   minAvgPowerFactorTypeSPF2,
                   minAvgPowerFactorPF2Date,
                   minAvgPowerFactorPF3,
                   minAvgPowerFactorTypeSPF3,
                   minAvgPowerFactorPF3Date
            }
    STATUS       current
    DESCRIPTION "Collection of Socomec Min Average metrology objects"
    ::= { socomecMinAveragesMIBGroups 1 }

socomecInstantaneousQualityMIBCompliance MODULE-COMPLIANCE
    STATUS       current
    DESCRIPTION "The compliance statement for Socomec instantaneous quality metrology table."
    MODULE    -- this module
    MANDATORY-GROUPS { socomecInstantaneousQualityGroup }
    ::= { socomecInstantaneousQualityMIBCompliances 1 }

socomecInstantaneousQualityGroup OBJECT-GROUP
    OBJECTS {
                -- Current THD
                   instTHDI1,
                   instTHDI2,
                   instTHDI3,
                   instTHDIn,
                   instMaxTHDI1,
                   instMaxTHDI1Date,
                   instMaxTHDI2,
                   instMaxTHDI2Date,
                   instMaxTHDI3,
                   instMaxTHDI3Date,
                   instMaxTHDIn,
                   instMaxTHDInDate,
                   instMinTHDI1,
                   instMinTHDI1Date,
                   instMinTHDI2,
                   instMinTHDI2Date,
                   instMinTHDI3,
                   instMinTHDI3Date,
                   instMinTHDIn,
                   instMinTHDInDate,
                -- Voltage THD
                   instTHDV1,
                   instTHDV2,
                   instTHDV3,
                   instTHDU12,
                   instTHDU23,
                   instTHDU31,
                   instMaxTHDV1,
                   instMaxTHDV1Date,
                   instMaxTHDV2,
                   instMaxTHDV2Date,
                   instMaxTHDV3,
                   instMaxTHDV3Date,
                   instMaxTHDU12,
                   instMaxTHDU12Date,
                   instMaxTHDU23,
                   instMaxTHDU23Date,
                   instMaxTHDU31,
                   instMaxTHDU31Date,
                   instMinTHDV1,
                   instMinTHDV1Date,
                   instMinTHDV2,
                   instMinTHDV2Date,
                   instMinTHDV3,
                   instMinTHDV3Date,
                   instMinTHDU12,
                   instMinTHDU12Date,
                   instMinTHDU23,
                   instMinTHDU23Date,
                   instMinTHDU31,
                   instMinTHDU31Date,
                -- Current Harmonics
                   instHarmonicsRow02I1,
                   instHarmonicsRow03I1,
                   instHarmonicsRow04I1,
                   instHarmonicsRow05I1,
                   instHarmonicsRow06I1,
                   instHarmonicsRow07I1,
                   instHarmonicsRow08I1,
                   instHarmonicsRow09I1,
                   instHarmonicsRow10I1,
                   instHarmonicsRow02I2,
                   instHarmonicsRow03I2,
                   instHarmonicsRow04I2,
                   instHarmonicsRow05I2,
                   instHarmonicsRow06I2,
                   instHarmonicsRow07I2,
                   instHarmonicsRow08I2,
                   instHarmonicsRow09I2,
                   instHarmonicsRow10I2,
                   instHarmonicsRow02I3,
                   instHarmonicsRow03I3,
                   instHarmonicsRow04I3,
                   instHarmonicsRow05I3,
                   instHarmonicsRow06I3,
                   instHarmonicsRow07I3,
                   instHarmonicsRow08I3,
                   instHarmonicsRow09I3,
                   instHarmonicsRow10I3,
                   instHarmonicsRow02In,
                   instHarmonicsRow03In,
                   instHarmonicsRow04In,
                   instHarmonicsRow05In,
                   instHarmonicsRow06In,
                   instHarmonicsRow07In,
                   instHarmonicsRow08In,
                   instHarmonicsRow09In,
                   instHarmonicsRow10In,
                -- Voltage Phase-Neutral Harmonics
                   instHarmonicsRow02V1,
                   instHarmonicsRow03V1,
                   instHarmonicsRow04V1,
                   instHarmonicsRow05V1,
                   instHarmonicsRow06V1,
                   instHarmonicsRow07V1,
                   instHarmonicsRow08V1,
                   instHarmonicsRow09V1,
                   instHarmonicsRow10V1,
                   instHarmonicsRow02V2,
                   instHarmonicsRow03V2,
                   instHarmonicsRow04V2,
                   instHarmonicsRow05V2,
                   instHarmonicsRow06V2,
                   instHarmonicsRow07V2,
                   instHarmonicsRow08V2,
                   instHarmonicsRow09V2,
                   instHarmonicsRow10V2,
                   instHarmonicsRow02V3,
                   instHarmonicsRow03V3,
                   instHarmonicsRow04V3,
                   instHarmonicsRow05V3,
                   instHarmonicsRow06V3,
                   instHarmonicsRow07V3,
                   instHarmonicsRow08V3,
                   instHarmonicsRow09V3,
                   instHarmonicsRow10V3,
                -- Voltage Phase-Phase Harmonics
                   instHarmonicsRow02U12,
                   instHarmonicsRow03U12,
                   instHarmonicsRow04U12,
                   instHarmonicsRow05U12,
                   instHarmonicsRow06U12,
                   instHarmonicsRow07U12,
                   instHarmonicsRow08U12,
                   instHarmonicsRow09U12,
                   instHarmonicsRow10U12,
                   instHarmonicsRow02U23,
                   instHarmonicsRow03U23,
                   instHarmonicsRow04U23,
                   instHarmonicsRow05U23,
                   instHarmonicsRow06U23,
                   instHarmonicsRow07U23,
                   instHarmonicsRow08U23,
                   instHarmonicsRow09U23,
                   instHarmonicsRow10U23,
                   instHarmonicsRow02U31,
                   instHarmonicsRow03U31,
                   instHarmonicsRow04U31,
                   instHarmonicsRow05U31,
                   instHarmonicsRow06U31,
                   instHarmonicsRow07U31,
                   instHarmonicsRow08U31,
                   instHarmonicsRow09U31,
                   instHarmonicsRow10U31
            }
    STATUS       current
    DESCRIPTION "Collection of Socomec instantaneous quality metrology objects"
    ::= { socomecInstantaneousQualityMIBGroups 1 }

socomecMetroDCMIBCompliance MODULE-COMPLIANCE
    STATUS       current
    DESCRIPTION "The compliance statement for Socomec DC Metrology table."
    MODULE    -- this module
    MANDATORY-GROUPS { socomecMetroDCGroup }
    ::= { socomecMetroDCMIBCompliances 1 }

socomecMetroDCGroup OBJECT-GROUP
    OBJECTS {
				   dcInstIrms                   ,
                   dcInstIdc                    ,
                   dcInstIripple                ,
				   dcAvgIrms                    ,
                   dcAvgIdc                     ,
                   dcAvgIripple                 ,
                                                
				   dcMaxInstIrms                ,
				   dcMaxInstIrmsDate            ,
                   dcMaxInstIdc                 ,
                   dcMaxInstIdcDate             ,
                   dcMaxInstIripple             ,
                   dcMaxInstIrippleDate         ,
				   dcMinInstIrms                ,
				   dcMinInstIrmsDate            ,
                   dcMinInstIdc                 ,
                   dcMinInstIdcDate             ,
                   dcMinInstIripple             ,
                   dcMinInstIrippleDate         ,
				   dcMaxAvgIrms                 ,
				   dcMaxAvgIrmsDate             ,
                   dcMaxAvgIdc                  ,
                   dcMaxAvgIdcDate              ,
                   dcMaxAvgIripple              ,
                   dcMaxAvgIrippleDate          ,
				   dcMinAvgIrms                 ,
				   dcMinAvgIrmsDate             ,
                   dcMinAvgIdc                  ,
                   dcMinAvgIdcDate              ,
                   dcMinAvgIripple              ,
                   dcMinAvgIrippleDate          ,
                                                
                   dcAvgDateLastInstance        ,
                                                
                   dcInstTotalPowerActive       ,
                   dcAvgTotalPowerActive        ,
                   dcMinInstTotalPowerActive    ,
                   dcMinInstTotalPowerActiveDate,
                   dcMaxInstTotalPowerActive    ,
                   dcMaxInstTotalPowerActiveDate,
                   dcMinAvgTotalPowerActive     ,
                   dcMinAvgTotalPowerActiveDate ,
                   dcMaxAvgTotalPowerActive     ,
                   dcMaxAvgTotalPowerActiveDate ,
                                                
				   dcInstVrms                   ,
                   dcInstVdc                    ,
                   dcInstVripple                ,
				   dcAvgVrms                    ,
                   dcAvgVdc                     ,
                   dcAvgVripple                 ,
                                                
				   dcMaxInstVrms                ,
				   dcMaxInstVrmsDate            ,
                   dcMaxInstVdc                 ,
                   dcMaxInstVdcDate             ,
                   dcMaxInstVripple             ,
                   dcMaxInstVrippleDate         ,
				   dcMinInstVrms                ,
				   dcMinInstVrmsDate            ,
                   dcMinInstVdc                 ,
                   dcMinInstVdcDate             ,
                   dcMinInstVripple             ,
                   dcMinInstVrippleDate         ,
				   dcMaxAvgVrms                 ,
				   dcMaxAvgVrmsDate             ,
                   dcMaxAvgVdc                  ,
                   dcMaxAvgVdcDate              ,
                   dcMaxAvgVripple              ,
                   dcMaxAvgVrippleDate          ,
				   dcMinAvgVrms                 ,
				   dcMinAvgVrmsDate             ,
                   dcMinAvgVdc                  ,
                   dcMinAvgVdcDate              ,
                   dcMinAvgVripple              ,
                   dcMinAvgVrippleDate
            }
    STATUS       current
    DESCRIPTION "Collection of Socomec DC Metrology objects"
    ::= { socomecMetroDCMIBGroups 1 }
	
socomecAtsMIBCompliance MODULE-COMPLIANCE
    STATUS       current
    DESCRIPTION "The compliance statement for Socomec Ats tables"
    MODULE    -- this module
    MANDATORY-GROUPS { socomecAtsMIBGroup }
    ::= { socomecAtsMIBCompliances 1 }

socomecAtsMIBGroup OBJECT-GROUP
    OBJECTS {
                    atsMetroLegacyVoltPhPhU12Source1         ,
                    atsMetroLegacyVoltPhPhU23Source1         ,
                    atsMetroLegacyVoltPhPhU31Source1         ,
                    atsMetroLegacyVoltPhNV1Source1           ,
                    atsMetroLegacyVoltPhNV2Source1           ,
                    atsMetroLegacyVoltPhNV3Source1           ,
                    atsMetroLegacyFrequencySource1           ,
                    atsMetroLegacyVoltPhPhU12Source2         ,
                    atsMetroLegacyVoltPhPhU23Source2         ,
                    atsMetroLegacyVoltPhPhU31Source2         ,
                    atsMetroLegacyVoltPhNV1Source2           ,
                    atsMetroLegacyVoltPhNV2Source2           ,
                    atsMetroLegacyVoltPhNV3Source2           ,
                    atsMetroLegacyFrequencySource2           ,
					
                    atsMetroVoltPhPhU12Source          ,
                    atsMetroVoltPhPhU23Source          ,
                    atsMetroVoltPhPhU31Source          ,
                    atsMetroVoltPhNV1Source            ,
                    atsMetroVoltPhNV2Source            ,
                    atsMetroVoltPhNV3Source            ,
                    atsMetroFrequencySource            ,
                    
                    atsStatusSourcePrio                ,
                    atsStatusSwitchAlarmFaultCode      ,
                    atsStatusSwitchOperatingMode       ,
                    atsStatusSwitchPosition            ,
                    atsStatusRelayStateSource1         ,
                    atsStatusRelayStateSource2         ,
                    atsStatusSwitchStateSource1        ,
                    atsStatusSwitchStateSource2        ,
                    atsStatusSwitchTestInProgress      ,
                    atsStatusCycleCounter              ,
                    atsStatusOperationCounterPos1      ,
                    atsStatusOperationCounterPos2      ,
                    atsStatusSwitchFaultSummary        ,
                    atsStatusSwitchLastCause           
            }
    STATUS       current
    DESCRIPTION "Collection of Socomec Ats objects"
    ::= { socomecAtsMIBGroups 1 }
	
socomecCommandMIBCompliance MODULE-COMPLIANCE
    STATUS       current
    DESCRIPTION "The compliance statement for Socomec Command tables"
    MODULE    -- this module
    MANDATORY-GROUPS { socomecCommandMIBGroup }
    ::= { socomecCommandMIBCompliances 1 }

socomecCommandMIBGroup OBJECT-GROUP
    OBJECTS {
                    commandAtsGensetStartOrder            ,
                    commandAtsPosition                    ,
                    commandAtsPriorityMode                ,
                    commandAtsOperatingMode               ,
                    commandAtsCommandAlarm
            }
    STATUS       current
    DESCRIPTION "Collection of Socomec Command objects"
    ::= { socomecCommandMIBGroups 1 }
    
    
socomecTrapsMIBCompliance MODULE-COMPLIANCE
    STATUS       current
    DESCRIPTION "The compliance statement for Socomec Traps table."
    MODULE    -- this module
    MANDATORY-GROUPS { socomecTrapsGroup }
    ::= { socomecTrapsMIBCompliances 1 }

socomecTrapsGroup NOTIFICATION-GROUP
    NOTIFICATIONS {
                    analogAlarms,
                    logicalAlarms,
                    combinationAlarms,
                    inrushAlarms,
                    eventsAlarms,
                    systemAlarms,
                    protectionAlarms,
                    faultAlarms,
                    rcmAlarms,
                    comparisonAlarms,
                    unknownAlarms
                  }
    STATUS       current
    DESCRIPTION "A collection of Socomec trap objects"
    ::= { socomecTrapsMIBGroups 2 }
    
END
